-- %CopyrightBegin%
--
-- SPDX-License-Identifier: LicenseRef-RSA-PKCS3
--
-- Copyright (C) The Internet Society (2000).  All Rights Reserved.
-- Copyright Ericsson AB 2010-2025. All Rights Reserved.
--
-- This document and translations of it may be copied and furnished to
-- others, and derivative works that comment on or otherwise explain it
-- or assist in its implementation may be prepared, copied, published
-- and distributed, in whole or in part, without restriction of any
-- kind, provided that the above copyright notice and this paragraph are
-- included on all such copies and derivative works.  However, this
-- document itself may not be modified in any way, such as by removing
-- the copyright notice or references to the Internet Society or other
-- Internet organizations, except as needed for the purpose of
-- developing Internet standards in which case the procedures for
-- copyrights defined in the Internet Standards process must be
-- followed, or as required to translate it into languages other than
-- English.
--
-- The limited permissions granted above are perpetual and will not be
-- revoked by the Internet Society or its successors or assigns.
--
-- This document and the information contained herein is provided on an
-- "AS IS" basis and THE INTERNET SOCIETY AND THE INTERNET ENGINEERING
-- TASK FORCE DISCLAIMS ALL WARRANTIES, EXPRESS OR IMPLIED, INCLUDING
-- BUT NOT LIMITED TO ANY WARRANTY THAT THE USE OF THE INFORMATION
-- HEREIN WILL NOT INFRINGE ANY RIGHTS OR ANY IMPLIED WARRANTIES OF
-- MERCHANTABILITY OR FITNESS FOR A PARTICULAR PURPOSE.
--
-- %CopyrightEnd%

PKCS-3 {
       iso(1) member-body(2) us(840) rsadsi(113549)
      pkcs(1) 3
}

DEFINITIONS EXPLICIT TAGS ::=

BEGIN

pkcs-3 OBJECT IDENTIFIER ::=
  { iso(1) member-body(2) us(840) rsadsi(113549)
      pkcs(1) 3 }

dhKeyAgreement OBJECT IDENTIFIER ::= { pkcs-3 1 }

DHParameter ::= SEQUENCE {
  prime INTEGER, -- p
  base INTEGER, -- g
  privateValueLength INTEGER OPTIONAL }

END
