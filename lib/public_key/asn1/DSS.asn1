-- %CopyrightBegin%
--
-- SPDX-License-Identifier: Apache-2.0
--
-- Copyright Ericsson AB 2008-2025. All Rights Reserved.
--
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
--
-- %CopyrightEnd%

DSS DEFINITIONS EXPLICIT TAGS ::=

BEGIN

-- EXPORTS ALL
-- All types and values defined in this module are exported for use
-- in other ASN.1 modules.

DSAPrivateKey ::= SEQUENCE {
    version           INTEGER,
    p                 INTEGER,  -- p
    q                 INTEGER,  -- q
    g                 INTEGER,  -- q
    y                 INTEGER,  -- y
    x                 INTEGER   -- x
}

END
