OrberCSIv2 DEFINITIONS ::=

BEGIN

 IMPORTS

 -- IMPORTed module OIDs MAY change if [PKIXPROF] changes
 -- PKIX1Explicit88 Certificate Extensions
    Certificate
    FROM PKIX1Explicit88 {iso(1) identified-organization(3)
         dod(6) internet(1) security(5) mechanisms(5)
         pkix(7) id-mod(0) id-pkix1-explicit-88(1)}
 -- PKIXAttributeCertificate
    AttributeCertificate
    FROM PKIXAttributeCertificate {iso(1) identified-organization(3) dod(6)
         internet(1) security(5) mechanisms(5) pkix(7) id-mod(0)
         id-mod-attribute-cert(12)};



 -- Authorization Token
 -- AttributeCertificate - [IETF ID PKIXAC].
 -- Certificate - [IETF RFC 2459].
            
    VerifyingCertChain ::= SEQUENCE OF Certificate
            
    AttributeCertChain ::= SEQUENCE {
  	attributeCert AttributeCertificate,
       	certificateChain VerifyingCertChain
    }


 -- The ASN.1 encoding of identity tokens of this type is defined
 -- as follows (ITTX509CertChain):
    CertificateChain ::= SEQUENCE SIZE (1..MAX) OF Certificate


 -- The object identifier allocated for the GSSUP mechanism is defined as follows:
 -- GSS Exported Name Object Form for GSSUP Mechanism
    gssup-mechanism  OBJECT IDENTIFIER ::= { iso-itu-t (2) international-organization (23) omg (130) security (1) authentication (1) gssup-mechanism (1) }

 -- Scoped-Username GSS Name Form
    scoped-username OBJECT IDENTIFIER ::= { iso-itu-t (2) international-organization (23) omg (130) security (1) naming (2) scoped-username(1) }

END
