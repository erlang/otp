Mod2 DEFINITIONS AUTOMATIC TAGS ::=

BEGIN

IMPORTS
    Stat,Country
    FROM Mod3
    L
    FROM Mod1
    Time,LocName,ThingName,Name
    FROM Mod4;
    
T ::= SEQUENCE {
  unit ENUMERATED{celsius,fahrenheit,kelvin},
  degree INTEGER,
  location L,
  time  Time,
  statistics Stat
}

OtherName ::= SEQUENCE {
  locationName LocName,
  thingName    ThingName
}

FirstName ::= CHOICE {
  firstname    PrintableString,
  nickname     PrintableString
}

FamilyName ::= SEQUENCE{
  prefix  ENUMERATED{none,von,af},
  secondname PrintableString
}

Lang ::= SEQUENCE{
  l PrintableString}

Inhabitant ::= SEQUENCE {
  name Name,
  country Country}

END
