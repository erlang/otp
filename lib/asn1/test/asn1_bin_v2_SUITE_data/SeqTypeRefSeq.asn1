SeqTypeRefSeq DEFINITIONS IMPLICIT TAGS ::= 

BEGIN

Seq1 ::= SEQUENCE 
{
  bool1  BOOLEAN,
  int1  INTEGER,
  seq1  SeqIn
}

Seq2 ::= SEQUENCE 
{
  seq2  SeqIn,
  bool2  BOOLEAN,
  int2  INTEGER
}

Seq3 ::= SEQUENCE 
{
  bool3  BOOLEAN,
  seq3  SeqIn,
  int3  INTEGER
}

Seq4 ::= SEQUENCE 
{
  seq41  SeqIn,
  seq42  SeqIn,
  seq43  SeqIn
}


SeqIn ::= SEQUENCE 
{
  boolIn  BOOLEAN,
  intIn  INTEGER
}


SeqS1 ::= SEQUENCE 
{
  boolS1  BOOLEAN,
  intS1  INTEGER,
  seqS1  SEQUENCE { boolIn BOOLEAN,
                    intIn  INTEGER }
}

SeqS2 ::= SEQUENCE 
{
  seqS2  SEQUENCE { boolIn BOOLEAN,
                    intIn  INTEGER },
  boolS2  BOOLEAN,
  intS2  INTEGER

}

SeqS3 ::= SEQUENCE 
{
  boolS3  BOOLEAN,
  seqS3  SEQUENCE { boolIn BOOLEAN,
                    intIn  INTEGER },
  intS3  INTEGER

}


SeqSTag ::= SEQUENCE 
{
  seqS1  SEQUENCE { b1 BOOLEAN,
                    i1  INTEGER },
  seqS2  [7] SEQUENCE { b2 BOOLEAN,
                        i2  INTEGER },
  seqS3  [8] EXPLICIT SEQUENCE { b3 BOOLEAN,
                                 i3  INTEGER }
}



SeqTRseq ::=  SEQUENCE 
{
  seqSeq SeqSeq,
  seqSeqI [134] SeqSeq,
  seqSeqE [135] EXPLICIT SeqSeq,

  seqSeq-I SeqSeqImp,
  seqSeqI-I [234] SeqSeqImp,
  seqSeqE-I [235] EXPLICIT SeqSeqImp,

  seqSeq-E SeqSeqExp,
  seqSeqI-E [334] SeqSeqExp,
  seqSeqE-E [335] EXPLICIT SeqSeqExp

}

SeqSeq ::= SEQUENCE {
		seqInt INTEGER,
		seqOs OCTET STRING
                }

SeqSeqImp ::= [64] SEQUENCE {
		seqInt INTEGER,
		seqOs OCTET STRING
                }

SeqSeqExp ::= [65] EXPLICIT SEQUENCE {
		seqInt INTEGER,
		seqOs OCTET STRING
                }



END
