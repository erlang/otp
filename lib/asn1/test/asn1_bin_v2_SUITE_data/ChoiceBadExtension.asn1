ChoiceBadExtension DEFINITIONS ::=
BEGIN

Seq ::= SEQUENCE {
    ...,
    name PrintableString,
    location INTEGER {home(0),field(1),roving(2)},
    age INTEGER 
    }

Cho1 ::= CHOICE {
    name PrintableString,
    ...,
    location INTEGER {home(0),field(1),roving(2)},
    age INTEGER 
    }

Cho2 ::= CHOICE {
    ...,
    name PrintableString,
    location INTEGER {home(0),field(1),roving(2)},
    age INTEGER 
    }

END
