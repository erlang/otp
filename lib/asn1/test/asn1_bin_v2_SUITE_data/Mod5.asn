Mod5 DEFINITIONS AUTOMATIC TAGS ::=

BEGIN

IMPORTS
    Country,RegionName,Inhabitants
    FROM Mod3;
TS ::= SEQUENCE {
  average  INTEGER,
  highest  INTEGER,
  lowest   INTEGER
}

RFS ::= SEQUENCE {
  average INTEGER,
  highest INTEGER
}

WS ::= SEQUENCE {
  average INTEGER,
  highest INTEGER
}

HS ::= SEQUENCE {
  average INTEGER,
  highest INTEGER,
  lowest INTEGER
}

Co ::= Country

Reg ::= SEQUENCE {
  name RegionName,
  inhabitants Inhabitants
}

END
