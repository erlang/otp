PrimStrings DEFINITIONS IMPLICIT TAGS ::= 

BEGIN

  Bs1 ::= BIT STRING
  Bs2 ::= BIT STRING {su(0), mo(1), tu(2), we(3), th(4), fr(5), sa(6) } (SIZE (7))
  Bs3 ::= BIT STRING {su(0), mo(1), tu(2), we(3), th(4), fr(5), sa(6) } (SIZE (1..7))
  Bs4 ::= BIT STRING {su(0), mo(1), tu(2), we(3), th(4), fr(5), sa(6) } (SIZE (1..32))
  Bs5 ::= BIT STRING {su(0), mo(17), tu(2), we(3), th(4), fr(5), sa(6) } (SIZE (1..32))
  Bs6 ::= BIT STRING {su(0), mo(17), tu(2), we(3), th(4), fr(5), sa(6)} (SIZE (16..32))
  Bs7 ::= BIT STRING (SIZE (24))
  BsPri ::= [PRIVATE 61] BIT STRING
  BsExpPri ::= [PRIVATE 61] EXPLICIT BIT STRING
  ODB-GeneralData ::= BIT STRING {
    allOG-CallsBarred         (0),
    internationalOGCallsBarred  (1),
    internationalOGCallsNotToHPLMN-CountryBarred  (2),
    interzonalOGCallsBarred   (6),
    interzonalOGCallsNotToHPLMN-CountryBarred (7),
    interzonalOGCallsAndInternationalOGCallsNotToHPLMN-CountryBarred (8),
    premiumRateInformationOGCallsBarred  (3),
    premiumRateEntertainementOGCallsBarred  (4),
    ss-AccessBarred  (5),
    allECT-Barred  (9),
    chargeableECT-Barred  (10),
    internationalECT-Barred  (11),
    interzonalECT-Barred  (12),
    doublyChargeableECT-Barred  (13),
    multipleECT-Barred  (14)} (SIZE (15..32))
    -- exception handling: reception of unknown bit assignments in the
    -- ODB-GeneralData type shall be treated like unsupported ODB-GeneralData

  TransportLayerAddress 	::= BIT STRING (SIZE (1..160, ...))
  
  --TestS is to test OTP-4353. See also x691 15.3 and x680 21.7
  TestS ::= BIT STRING {a(0),b(1)} (SIZE (3..8))
  
  -- OTP-5932
  BSMAX ::= BIT STRING (SIZE (5..MAX))
  
  -- OTP-7602
  
BS255 ::= BIT STRING (SIZE (255))

BS256 ::= BIT STRING (SIZE (256))

BS1024 ::= BIT STRING (SIZE (1024))

  

  Os ::= OCTET STRING
  OsCon ::= [60] OCTET STRING
  OsPri ::= [PRIVATE 61] OCTET STRING
  OsApp ::= [APPLICATION 62] OCTET STRING
  OsExpCon ::= [60] EXPLICIT OCTET STRING
  OsExpPri ::= [PRIVATE 61] EXPLICIT  OCTET STRING
  OsExpApp ::= [APPLICATION 62] EXPLICIT OCTET STRING

  Ns ::= NumericString
  NsCon ::= [70] NumericString
  NsExpCon ::= [71] EXPLICIT NumericString

  Ps ::= PrintableString

  Ts ::= TeletexString

  Vxs ::= VideotexString

  Vis ::= VisibleString

  IA5 ::= IA5String

  Grs ::= GraphicString
  
  ODesc ::= ObjectDescriptor

  ODescSeq ::= SEQUENCE {
		o ObjectDescriptor OPTIONAL,
		i INTEGER
  }

  Ges ::= GeneralString

  Us ::= UniversalString
  UsCon ::= [70] UniversalString
  UsExpCon ::= [71] EXPLICIT UniversalString

  BMP ::= BMPString

  Gt ::= GeneralizedTime

  UTC ::= UTCTime
  
  UTF ::= UTF8String


END
