Prim DEFINITIONS IMPLICIT TAGS ::= 

BEGIN

  Bool ::=  BOOLEAN
  BoolCon ::=  [20] BOOLEAN
  BoolPri ::=  [PRIVATE 21] BOOLEAN
  BoolApp ::=  [APPLICATION 22] BOOLEAN
  BoolExpCon ::=  [30] EXPLICIT BOOLEAN
  BoolExpPri ::=  [PRIVATE 31] EXPLICIT BOOLEAN
  BoolExpApp ::=  [APPLICATION 32] EXPLICIT BOOLEAN

  Int ::=  INTEGER
  IntCon ::=  [40] INTEGER
  IntPri ::=  [PRIVATE 41] INTEGER
  IntApp ::=  [APPLICATION 42] INTEGER
  IntExpCon ::=  [50] EXPLICIT INTEGER
  IntExpPri ::=  [PRIVATE 51] EXPLICIT INTEGER
  IntExpApp ::=  [APPLICATION 52] EXPLICIT INTEGER

  IntEnum ::=  INTEGER {first(1),last(31)}

  Enum ::=  ENUMERATED {monday(1),tuesday(2),wednesday(3),thursday(4),
                        friday(5),saturday(6),sunday(7)}

  ObjId ::= OBJECT IDENTIFIER
  
  RelOid ::= RELATIVE-OID

  Null ::= NULL

END
