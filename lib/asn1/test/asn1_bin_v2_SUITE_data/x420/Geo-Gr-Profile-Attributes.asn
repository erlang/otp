-- Module Geo-Gr-Profile-Attributes (T.418:03/1993)

Geo-Gr-Profile-Attributes {2 8 1 8 4} DEFINITIONS IMPLICIT TAGS ::=
BEGIN

EXPORTS
  Geo-Gr-Presentation-Feature, Geo-Gr-Coding-Attribute, Geo-Gr-Content-Defaults;

IMPORTS
  Line-Rendition, Marker-Rendition, Text-Rendition, Filled-Area-Rendition,
    Edge-Rendition, Colour-Representations, Transparency-Specification,
    Transformation-Specification, Region-Of-Interest-Specification,
    Picture-Orientation, Picture-Dimensions, ASF-Type, VDC-Pair,
    One-Of-Four-Angles
    FROM Geo-Gr-Presentation-Attributes {2 8 1 8 2}; -- see 10.2

Geo-Gr-Presentation-Feature ::= CHOICE {
  null            NULL,
  text-rendition  [3]  Text-Rendition
}

Geo-Gr-Coding-Attribute ::= NULL

-- no non-basic values are defined for the
-- geometric graphics coding attributes in this Specification
Geo-Gr-Content-Defaults ::= SET {
  line-rendition                    [1]  Line-Rendition OPTIONAL,
  marker-rendition                  [2]  Marker-Rendition OPTIONAL,
  text-rendition                    [3]  Text-Rendition OPTIONAL,
  filled-area-rendition             [4]  Filled-Area-Rendition OPTIONAL,
  edge-rendition                    [5]  Edge-Rendition OPTIONAL,
  colour-representations            [6]  Colour-Representations OPTIONAL,
  transparency-specification        [7]  Transparency-Specification OPTIONAL,
  transformation-specification      [8]  Transformation-Specification OPTIONAL,
  region-of-interest-specification
    [9]  Region-Of-Interest-Specification OPTIONAL,
  picture-orientation               [10]  Picture-Orientation OPTIONAL,
  picture-dimensions                [11]  Picture-Dimensions OPTIONAL
}

END

-- Generated by Asnp, the ASN.1 pretty-printer of France Telecom R&D
