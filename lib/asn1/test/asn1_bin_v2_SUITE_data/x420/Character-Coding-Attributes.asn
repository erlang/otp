-- Module Character-Coding-Attributes (T.416:03/1993)

Character-Coding-Attributes {2 8 1 6 3} DEFINITIONS ::=
BEGIN

EXPORTS Character-Coding-Attributes;

Character-Coding-Attributes ::= SET {
}

--	no character coding attributes 
--	are defined in this part of
--	ITU-T Rec. T.410-Series | ISO/IEC 8613
END

-- Generated by Asnp, the ASN.1 pretty-printer of France Telecom R&D
