-- Module IPMSFunctionalObjects (X.420:06/1999)
IPMSFunctionalObjects {joint-iso-itu-t mhs(6) ipms(1) modules(0)
  functional-objects(1) version-1994(0)} DEFINITIONS IMPLICIT TAGS ::=
BEGIN

-- Prologue
-- Exports everything.
IMPORTS
  -- IPMS Abstract Service
  management, origination, reception
    --==
    FROM IPMSAbstractService {joint-iso-itu-t mhs(6) ipms(1) modules(0)
      abstract-service(3) version-1994(0)}
  -- IPMS Object Identifiers
  id-ot-ipms, id-ot-ipms-user
    --==
    FROM IPMSObjectIdentifiers {joint-iso-itu-t mhs(6) ipms(1) modules(0)
      object-identifiers(0) version-1999(1)}
  -- MTS Abstract Service
  MHS-OBJECT
    --==
    FROM MTSAbstractService {joint-iso-itu-t mhs(6) mts(3) modules(0)
      mts-abstract-service(1) version-1999(1)}
  -- Remote Operations
  CONTRACT
    --==
    FROM Remote-Operations-Information-Objects {joint-iso-itu-t
      remote-operations(4) informationObjects(5) version1(0)};

-- Primary object types
ipms-user MHS-OBJECT ::= {
  INITIATES  {ipms-access-contract}
  ID         id-ot-ipms-user
}

ipms-access-contract CONTRACT ::= {
  INITIATOR CONSUMER OF  {origination | reception | management}
}

ipms MHS-OBJECT ::= {RESPONDS  {ipms-access-contract}
                     ID        id-ot-ipms
}

END -- of IPMSFunctionalObjects

-- Generated by Asnp, the ASN.1 pretty-printer of France Telecom R&D
