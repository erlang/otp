-- Module Raster-Gr-Presentation-Attributes (T.417:03/1993)

Raster-Gr-Presentation-Attributes {2 8 1 7 2} DEFINITIONS ::=
BEGIN

EXPORTS
  Raster-Graphics-Attributes, Clipping, Measure-Pair, One-Of-Four-Angles,
    One-Of-Two-Angles, Pel-Transmission-Density, Pel-Spacing, Spacing-Ratio,
    Image-Dimensions, Coordinate-Pair;

Raster-Graphics-Attributes ::= SET {
  pel-path                  [0] IMPLICIT One-Of-Four-Angles OPTIONAL,
  line-progression          [1] IMPLICIT One-Of-Two-Angles OPTIONAL,
  pel-transmission-density  [2] IMPLICIT Pel-Transmission-Density OPTIONAL,
  initial-offset            [3] IMPLICIT Measure-Pair OPTIONAL,
  clipping                  [4] IMPLICIT Clipping OPTIONAL,
  pel-spacing               [5]  Pel-Spacing OPTIONAL,
  spacing-ratio             [6] IMPLICIT Spacing-Ratio OPTIONAL,
  image-dimensions          [7]  Image-Dimensions OPTIONAL
}

One-Of-Four-Angles ::= INTEGER {
  d0(0), -- d0
  d90(1), -- d90
  d180(2), --d180
  d270(3) -- d270--}

One-Of-Two-Angles ::= INTEGER {d90(1), -- d90
                               d270(3) -- d270 --}

Pel-Transmission-Density ::= INTEGER {
  p5(2), -- 5 BMU (240 pels/25.4 mm)
  p4(3), -- 4 BMU (300 pels/25.4 mm)
  p3(4), -- 3 BMU (400 pels/25.4 mm)
  p2(5), -- 2 BMU (600 pels/25.4 mm)
  p1(6), -- 1 BMU (1200 pels/25.4 mm)
  colour-grey-scale-p12(10), -- 12 BMU (100 pels/25.4 mm)
  colour-grey-scale-p6(11), -- 6 BMU (200 pels/25.4 mm)
  colour-grey-scale-p4(13), -- 4 BMU (300 pels/25.4 mm)
  colour-grey-scale-p3(14), -- 3 BMU (400 pels/25.4 mm)
  colour-grey-scale-p2(15), -- 2 BMU (600 pels/25.4 mm)
  colour-grey-scale-p1(16), -- 1 BMU (1200 pels/25.4 mm)
  p6(1)} -- 6 BMU (200 pels/25.4 mm)

-- default and basic value is p6 (1) 
Measure-Pair ::= SEQUENCE {
  horizontal  [0] IMPLICIT INTEGER,
  vertical    [0] IMPLICIT INTEGER
}

Clipping ::= SEQUENCE {
  first-coordinate-pair   [0] IMPLICIT Coordinate-Pair OPTIONAL,
  second-coordinate-pair  [1] IMPLICIT Coordinate-Pair OPTIONAL
}

Coordinate-Pair ::= SEQUENCE {x-coordinate  INTEGER,
                              y-coordinate  INTEGER
}

Pel-Spacing ::= CHOICE {
  spacing
    [0] IMPLICIT SEQUENCE {length      [0]  INTEGER,
                           pel-spaces  [0]  INTEGER},
  null     [1] IMPLICIT NULL
}

Spacing-Ratio ::= SEQUENCE {
  line-spacing-value  INTEGER,
  pel-spacing-value   INTEGER
}

Image-Dimensions ::= CHOICE {
  width-controlled
    [0] IMPLICIT SEQUENCE {minimum-width    [0]  INTEGER,
                           preferred-width  [0]  INTEGER},
  height-controlled
    [1] IMPLICIT SEQUENCE {minimum-height    INTEGER,
                           preferred-height  INTEGER},
  area-controlled
    [2] IMPLICIT SEQUENCE {minimum-width      INTEGER,
                           preferred-width    INTEGER,
                           minimum-height     INTEGER,
                           preferred-height   INTEGER,
                           aspect-ratio-flag  INTEGER {fixed(0), variable(1)}
  },
  automatic          [3] IMPLICIT NULL
}

END

-- Generated by Asnp, the ASN.1 pretty-printer of France Telecom R&D
