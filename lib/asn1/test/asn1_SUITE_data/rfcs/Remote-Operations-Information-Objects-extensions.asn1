-- Module Remote-Operations-Information-Objects-extensions (X.881:07/1994)

Remote-Operations-Information-Objects-extensions {joint-iso-itu-t
  remote-operations(4) informationObjects-extensions(8) version1(0)}
DEFINITIONS ::=
BEGIN

-- exports everything
IMPORTS
  CONTRACT
    FROM Remote-Operations-Information-Objects {joint-iso-itu-t
      remote-operations(4) informationObjects(5) version1(0)};

APPLICATION-CONTEXT ::= CLASS {
  &associationContract     CONTRACT,
  &associationRealization  REALIZATION OPTIONAL,
  &transferRealization     REALIZATION,
  &AbstractSyntaxes        ABSTRACT-SYNTAX,
  &applicationContextName  OBJECT IDENTIFIER UNIQUE
}
WITH SYNTAX {
  CONTRACT &associationContract
  [ESTABLISHED BY &associationRealization]
  INFORMATION TRANSFER BY &transferRealization
  ABSTRACT SYNTAXES &AbstractSyntaxes
  APPLICATION CONTEXT NAME &applicationContextName
}

REALIZATION ::= TYPE-IDENTIFIER

-- information objects ABSTRACT-SYNTAX and TYPE-IDENTIFIER are defined in ITU-T Rec. X.681 |
-- ISO/IEC 8824-2
END -- end of the information-objects-extensions module

-- Generated by Asnp, the ASN.1 pretty-printer of France Telecom R&D
