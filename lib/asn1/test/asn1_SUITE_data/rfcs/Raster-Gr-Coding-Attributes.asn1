-- Module Raster-Gr-Coding-Attributes (T.417:03/1993)

Raster-Gr-Coding-Attributes {2 8 1 7 3} DEFINITIONS ::=
BEGIN

EXPORTS
  Raster-Gr-Coding-Attributes, Compression, Tile-Type,
    Bits-Per-Colour-Component, Subsampling;

IMPORTS Coordinate-Pair
          FROM Raster-Gr-Presentation-Attributes {2 8 1 7 2};

Raster-Gr-Coding-Attributes ::= SET {
  number-of-pels-per-line       [0] IMPLICIT INTEGER OPTIONAL,
  number-of-lines               [1] IMPLICIT INTEGER OPTIONAL,
  compression                   [2] IMPLICIT Compression OPTIONAL,
  number-of-discarded-pels      [3] IMPLICIT INTEGER OPTIONAL,
  bits-per-colour-component     [4]  Bits-Per-Colour-Component OPTIONAL,
  interleaving-format
    [5] IMPLICIT INTEGER {pel(0), line(1), plane(2), stripe(3)} OPTIONAL,
  number-of-pels-per-tile-line  [6] IMPLICIT INTEGER OPTIONAL,
  number-of-lines-per-tile      [7] IMPLICIT INTEGER OPTIONAL,
  tiling-offset                 [8] IMPLICIT Coordinate-Pair OPTIONAL,
  tile-types                    [9] IMPLICIT SEQUENCE OF Tile-Type OPTIONAL,
  subsampling                   [10] IMPLICIT Subsampling OPTIONAL,
  jpeg-coding-mode
    [11] IMPLICIT INTEGER {-- Huffman coding
                           baseline(0), huffman-extended-sequential-DCT(1),
                           huffman-progressive-DCT(2),
                           huffman-spatial-lossless(3),
                           -- arithmetic coding
                           arithmetic-extended-sequential-DCT(9),
                           arithmetic-progressive-DCT(10),
                           arithmetic-spatial-lossless(11)},
  jpeg-quantization-table
    [12] IMPLICIT INTEGER {associated(0), default(1)} OPTIONAL,
  jpeg-huffman-table
    [13] IMPLICIT INTEGER {associated(0), preferred(1)},
  -- basic and default value is "associated".
  jbig-differential-layer
    [17] IMPLICIT INTEGER {dl-not-present(0), dl-encoded-without-tp-and-dp(1),
                           dl-encoded-with-tp(2), dl-encoded-with-dp(3),
                           dl-encoded-with-dp-and-private-dp-table(4),
                           dl-encoded-with-tp-and-dp(5),
                           dl-encoded-with-tp-dp-and-private-dp-table(6)}
      OPTIONAL,
  number-of-lines-per-stripe    [18] IMPLICIT INTEGER OPTIONAL
}

Compression ::= INTEGER {uncompressed(0), compressed(1)}

Tile-Type ::= INTEGER {
  null-background(0), null-foreground(1), t6-encoded(2),
  t4-one-dimensional-encoded(3), t4-two-dimensional-encoded(4),
  bitmap-encoded(5), t6-encoded-msb(6), t4-one-dimensional-encoded-msb(7),
  t4-two-dimensional-encoded-msb(8), jbig-bits-per-component-eq-1(9), 
  jpeg(10), jbig-bits-per-component-gr-1(11)}

Bits-Per-Colour-Component ::= CHOICE {
  single-integer  INTEGER,
  component-list  SEQUENCE OF INTEGER
}

Subsampling ::= OCTET STRING

-- The value OCTET STRING shall be chosen from the
-- following table:
-- Semantic Meaning	JPEG notations	Octet strings
--  4:1:1	((2,2),(1,1),(1,1))	  '221111'H
--  2:1:1 or 4:2:2	((2,1),(1,1),(1,1))	  '211111'H
--  1:1:1	((1,1),(1,1),(1,1))	  '111111'H
END

-- Generated by Asnp, the ASN.1 pretty-printer of France Telecom R&D
