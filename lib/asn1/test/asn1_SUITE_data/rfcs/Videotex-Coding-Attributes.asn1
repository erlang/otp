-- Module Videotex-Coding-Attributes (T.101:11/1994)
Videotex-Coding-Attributes DEFINITIONS ::=
BEGIN

EXPORTS Videotex-Coding-Attributes;

Videotex-Coding-Attributes ::= SET {
  subset   [0] IMPLICIT Subset OPTIONAL,
  rank     [1] IMPLICIT Rank OPTIONAL,
  profile  [2] IMPLICIT Profile OPTIONAL
}

Subset ::= INTEGER {
  undefined(0), rank1(1), rank2(2), rank3(3), rank4(4), rank5(5), profile1(81),
  profile2(82), profile3(83), profile4(84), profileX1-1(85), profileX1-2(86),
  profileX1-3(87), profileX1-4(88), profileX2-1(89), profileX2-2(90),
  profileX2-3(91), profileX2-4(92)}

Rank ::= INTEGER {
  undefined(0), rank1(1), rank2(2), rank3(3), rank4(4), rank5(5)}

Profile ::= INTEGER {
  undefined(0), profile1(81), profile2(82), profile3(83), profile4(84),
  profileX1-1(85), profileX1-2(86), profileX1-3(87), profileX1-4(88),
  profileX2-1(89), profileX2-2(90), profileX2-3(91), profileX2-4(92)}

END

-- Generated by Asnp, the ASN.1 pretty-printer of France Telecom R&D
