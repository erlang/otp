-- Module GULSProtectionMappings (X.830:04/1995)

GULSProtectionMappings {joint-iso-itu-t genericULS(20) modules(1)
  gulsProtectionMappings(5)} DEFINITIONS AUTOMATIC TAGS ::=
BEGIN

-- These protection mappings are more versatile that the
-- preceding protection mappings which were specifically designed
-- to generate identical bit-encodings as the Directory
-- Authentication Framework parameterized types.
-- EXPORTS All 
IMPORTS
  notation, gulsSecurityTransformations
    FROM ObjectIdentifiers {joint-iso-itu-t genericULS(20) modules(1)
      objectIdentifiers(0)}
  PROTECTION-MAPPING
    FROM Notation notation
  dirEncryptedTransformation, gulsSignedTransformation{},
    gulsSignatureTransformation, symmetricKeyInformation,
    asymmetricKeyInformation
    FROM GulsSecurityTransformations gulsSecurityTransformations;

-- ********************************** 
-- confidentiality Protection Mapping 
-- ********************************** 
-- This protection mapping enables the notation
-- PROTECTED {BaseType, confidentiality}
-- to map to either dirEncryptedTransformation or to no transformation
-- at the choice of the encoding system, dependent upon local security
-- policy and other local environment considerations.
-- Security Service:  confidentiality
confidentiality PROTECTION-MAPPING ::= {
  SECURITY-TRANSFORMATION  {dirEncryptedTransformation}
  BYPASS-PERMITTED         TRUE
}

-- ****************************** 
-- GULS signed Protection Mapping 
-- ****************************** 
-- This protection mapping causes the notation
-- PROTECTED {BaseType, signed}
-- to map to the gulsSignedTransformation.
-- Security Service:  data origin authentication, data integrity and
-- (in certain situations) non-repudiation.
signed PROTECTION-MAPPING ::= {
  SECURITY-TRANSFORMATION
    {gulsSignedTransformation
       {{symmetricKeyInformation | asymmetricKeyInformation}}}
}

-- ********************************* 
-- GULS signature Protection Mapping 
-- ********************************* 
-- This protection mapping causes the notation
-- PROTECTED {BaseType, signature}
-- to map to the gulsSignatureTransformation.
-- Security Service:  data origin authentication, data integrity and
-- (in certain situations) non-repudiation.
signature PROTECTION-MAPPING ::= {
  SECURITY-TRANSFORMATION
    {gulsSignatureTransformation
       {{symmetricKeyInformation | asymmetricKeyInformation}}}
}

END

-- Generated by Asnp, the ASN.1 pretty-printer of France Telecom R&D


-- content of stack:
--
