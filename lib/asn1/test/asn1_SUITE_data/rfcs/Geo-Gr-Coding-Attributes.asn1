-- Module Geo-Gr-Coding-Attributes (T.418:03/1993)

Geo-Gr-Coding-Attributes {2 8 1 8 3} DEFINITIONS ::=
BEGIN

EXPORTS Geo-Gr-Coding-Attributes;

Geo-Gr-Coding-Attributes ::= SET {
}

-- no geometric graphics coding attributes are defined
-- in this Specification
END

-- Generated by Asnp, the ASN.1 pretty-printer of France Telecom R&D
