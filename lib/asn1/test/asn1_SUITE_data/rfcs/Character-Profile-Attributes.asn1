-- Module Character-Profile-Attributes (T.416:03/1993)

Character-Profile-Attributes {2 8 1 6 4} DEFINITIONS ::=
BEGIN

EXPORTS
  Character-Presentation-Feature, Character-Coding-Attribute,
    Character-Content-Defaults;

IMPORTS
  Character-Attributes, One-Of-Four-Angles, One-Of-Two-Angles, Measure-Pair,
    Alignment, Layout-Table, Graphic-Rendition, Formatting-Indicator,
    Character-Fonts, Itemization, Kerning-Offset, Proportional-Line-Spacing,
    Pairwise-Kerning
    FROM Character-Presentation-Attributes;

--	see 11.2
Character-Presentation-Feature ::= CHOICE {
  character-path              [0] IMPLICIT One-Of-Four-Angles,
  line-progression            [1] IMPLICIT One-Of-Two-Angles,
  character-orientation       [2] IMPLICIT One-Of-Four-Angles,
  initial-offset              [3] IMPLICIT Measure-Pair,
  character-spacing           [6] IMPLICIT INTEGER,
  line-spacing                [7] IMPLICIT INTEGER,
  alignment                   [8] IMPLICIT Alignment,
  line-layout-table           [9] IMPLICIT Layout-Table,
  graphic-rendition           [10] IMPLICIT Graphic-Rendition,
  formatting-indicator        [11] IMPLICIT Formatting-Indicator,
  character-fonts             [12] IMPLICIT Character-Fonts,
  graphic-char-subrepertoire  [13] IMPLICIT INTEGER,
  itemization                 [14] IMPLICIT Itemization,
  widow-size                  [15] IMPLICIT INTEGER,
  orphan-size                 [16] IMPLICIT INTEGER,
  graphic-character-sets      [17] IMPLICIT OCTET STRING,
  indentation                 [19] IMPLICIT INTEGER,
  kerning-offset              [20] IMPLICIT Kerning-Offset,
  proportional-line-spacing   [21] IMPLICIT Proportional-Line-Spacing,
  pairwise-kerning            [22] IMPLICIT Pairwise-Kerning,
  first-line-offset           [23] IMPLICIT INTEGER,
  code-extension-announcers   [24] IMPLICIT OCTET STRING
}

Character-Coding-Attribute ::= NULL

--	no character coding attributes 
--	are defined in this part of
--	ITU-T Rec. T.410-Series | ISO/IEC 8613
Character-Content-Defaults ::=
  Character-Attributes

END

-- Generated by Asnp, the ASN.1 pretty-printer of France Telecom R&D
