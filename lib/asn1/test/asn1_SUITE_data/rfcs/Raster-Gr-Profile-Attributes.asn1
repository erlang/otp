-- Module Raster-Gr-Profile-Attributes (T.417:03/1993)

Raster-Gr-Profile-Attributes {2 8 1 7 4} DEFINITIONS ::=
BEGIN

EXPORTS
  Ra-Gr-Presentation-Feature, Ra-Gr-Coding-Attribute,
    Raster-Gr-Content-Defaults;

IMPORTS
  One-Of-Four-Angles, One-Of-Two-Angles, Pel-Transmission-Density,
    Measure-Pair, Clipping, Pel-Spacing, Spacing-Ratio, Image-Dimensions,
    Coordinate-Pair, Raster-Graphics-Attributes
    FROM Raster-Gr-Presentation-Attributes {2 8 1 7 2}
  Compression, Tile-Type, Bits-Per-Colour-Component, Subsampling
    FROM Raster-Gr-Coding-Attributes {2 8 1 7 3};

Ra-Gr-Coding-Attribute ::= CHOICE {
  compression                   [0] IMPLICIT Compression,
  bits-per-colour-component     [4]  Bits-Per-Colour-Component,
  interleaving-format
    [5] IMPLICIT INTEGER {pel(0), line(1), plane(2), stripe(3)},
  number-of-pels-per-tile-line  [6] IMPLICIT INTEGER,
  number-of-lines-per-tile      [7] IMPLICIT INTEGER,
  tiling-offset                 [8] IMPLICIT Coordinate-Pair,
  tiling-types                  [9] IMPLICIT Tile-Type,
  subsampling                   [10] IMPLICIT Subsampling,
  jpeg-coding-mode
    [11] IMPLICIT INTEGER {-- Huffman coding 
                           huffman-baseline(0),
                           huffman-extended-sequential-DCT(1),
                           huffman-progressive-DCT(2),
                           huffman-spatial-lossless(3),
                           -- arithmetic coding
                           arithmetic-progressive-DCT(10),
                           arithmetic-spatial-lossless(11)},
  jpeg-quantization-table
    [12] IMPLICIT INTEGER {associated(0), default(1)},
  jpeg-huffman-table
    [13] IMPLICIT INTEGER {associated(0), preferred(1)},
  jbig-tp-for-base-layer        [14] IMPLICIT INTEGER {not-used(0), used(1)},
  jbig-differential-layer
    [15] IMPLICIT INTEGER {dl-not-present(0), dl-encoded-without-tp-and-dp(1),
                           dl-encoded-with-tp(2), dl-encoded-with-dp(3),
                           dl-encoded-with-dp-and-private-dp-table(4),
                           dl-encoded-with-tp-and-dp(5),
                           dl-encoded-with-tp-dp-and-private-dp-table(6)},
  number-of-lines-per-stripe    [16] IMPLICIT INTEGER
}

Ra-Gr-Presentation-Feature ::= CHOICE {
  initial-offset            [3] IMPLICIT Measure-Pair,
  clipping                  [4] IMPLICIT Clipping,
  pel-spacing               [5]  Pel-Spacing,
  spacing-ratio             [6] IMPLICIT Spacing-Ratio,
  image-dimensions          [7]  Image-Dimensions,
  pel-path                  [9] IMPLICIT One-Of-Four-Angles,
  line-progression          [10] IMPLICIT One-Of-Two-Angles,
  pel-transmission-density  [11] IMPLICIT Pel-Transmission-Density
}

-- The tag values used above preserve compatibility
-- with Group 4 Class I facsimile data streams.
Raster-Gr-Content-Defaults ::= SET {
  COMPONENTS OF Raster-Graphics-Attributes,
  compression                   [8] IMPLICIT Compression OPTIONAL,
  number-of-pels-per-tile-line  [11] IMPLICIT INTEGER OPTIONAL,
  number-of-lines-per-tile      [12] IMPLICIT INTEGER OPTIONAL,
  tiling-offset                 [13] IMPLICIT Coordinate-Pair OPTIONAL,
  tiling-type                   [14] IMPLICIT Tile-Type OPTIONAL
}

END

-- Generated by Asnp, the ASN.1 pretty-printer of France Telecom R&D
