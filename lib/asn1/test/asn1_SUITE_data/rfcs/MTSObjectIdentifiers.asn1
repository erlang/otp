-- Module MTSObjectIdentifiers (X.411:06/1999)
MTSObjectIdentifiers {joint-iso-itu-t mhs(6) mts(3) modules(0)
  object-identifiers(0) version-1999(1)} DEFINITIONS IMPLICIT TAGS ::=
BEGIN

--	Prologue
--	Exports everything
IMPORTS -- nothing -- ;

ID ::= OBJECT IDENTIFIER

--	Message Transfer System
id-mts ID ::=
  {joint-iso-itu-t mhs(6) mts(3)} -- not definitive

--	Categories of Object Identifiers
id-mod ID ::= {id-mts  0} -- modules

id-ot ID ::= {id-mts  1} -- object types

id-pt ID ::= {id-mts  2} -- port types

id-cont ID ::= {id-mts  3} -- content types

id-eit ID ::= {id-mts  4} -- encoded information types

id-att ID ::= {id-mts  5} -- attributes

id-tok ID ::= {id-mts  6} -- token types

id-sa ID ::= {id-mts  7} -- secure agent types

id-ct ID ::= {id-mts  8} -- contracts

id-cp ID ::= {id-mts  9} -- connection packages

--	Modules
id-mod-object-identifiers ID ::= {id-mod  0} -- not definitive

id-mod-mts-abstract-service ID ::= {id-mod  1} -- not definitive

id-mod-mta-abstract-service ID ::= {id-mod  2} -- not definitive

id-mod-upper-bounds ID ::= {id-mod  3} -- not definitive

--	Object Types
id-ot-mts ID ::= {id-ot  0}

id-ot-mts-user ID ::= {id-ot  1}

id-ot-mta ID ::= {id-ot  2}

--	Port Types
id-pt-submission ID ::= {id-pt  0}

id-pt-delivery ID ::= {id-pt  1}

id-pt-administration ID ::= {id-pt  2}

id-pt-transfer ID ::= {id-pt  3}

--	Content Types
id-cont-unidentified ID ::=
  {id-cont  0} -- For use by MS and Directory

id-cont-inner-envelope ID ::= {id-cont  1}

--	Encoded Information Types
id-eit-unknown ID ::= {id-eit  0}

--  Value { id-eit 1 } is no longer defined
id-eit-ia5-text ID ::= {id-eit  2}

id-eit-g3-facsimile ID ::= {id-eit  3}

id-eit-g4-class-1 ID ::= {id-eit  4}

id-eit-teletex ID ::= {id-eit  5}

id-eit-videotex ID ::= {id-eit  6}

id-eit-voice ID ::= {id-eit  7}

id-eit-sfd ID ::= {id-eit  8}

id-eit-mixed-mode ID ::= {id-eit  9}

--	Attributes
id-att-physicalRendition-basic ID ::= {id-att  0}

id-att-physicalRendition-no-cover-page ID ::= {id-att  1}

--	Token Types
id-tok-asymmetricToken ID ::= {id-tok  0}

--	Secure Agent Types
id-sa-ua ID ::= {id-sa  0}

id-sa-ms ID ::= {id-sa  1}

--	Contracts
id-ct-mts-access ID ::= {id-ct  0}

id-ct-mts-forced-access ID ::= {id-ct  1}

id-ct-mta-transfer ID ::= {id-ct  2}

--	Connection Packages
id-cp-mts-connect ID ::= {id-cp  0}

id-cp-mta-connect ID ::= {id-cp  1}

END -- of MTSObjectIdentifiers

-- Generated by Asnp, the ASN.1 pretty-printer of France Telecom R&D
