-- Module IPMSExtendedBodyPartTypes2 (X.420:06/1999)
IPMSExtendedBodyPartTypes2 {iso standard mhs(10021) ipms(7) modules(0)
  extended-body-part-types-2(1)} DEFINITIONS IMPLICIT TAGS ::=
BEGIN

-- Prologue
-- Exports everything.
IMPORTS
  -- IPMS Information Objects
  EXTENDED-BODY-PART-TYPE
    --==
    FROM IPMSInformationObjects {joint-iso-itu-t mhs(6) ipms(1) modules(0)
      information-objects(2) version-1999(1)}
  -- IPMS Object Identifiers
  id-ep-general-text, id-et-general-text
    --==
    FROM IPMSObjectIdentifiers {joint-iso-itu-t mhs(6) ipms(1) modules(0)
      object-identifiers(0) version-1999(1)};

-- General Text body part
general-text-body-part EXTENDED-BODY-PART-TYPE ::= {
  PARAMETERS  {GeneralTextParameters
               IDENTIFIED BY  id-ep-general-text},
  DATA        {GeneralTextData
               IDENTIFIED BY  id-et-general-text}
}

GeneralTextParameters ::= SET OF CharacterSetRegistration

GeneralTextData ::= GeneralString

CharacterSetRegistration ::= INTEGER(1..32767)

END -- of IPMSExtendedBodyPartTypes2

-- Generated by Asnp, the ASN.1 pretty-printer of France Telecom R&D
