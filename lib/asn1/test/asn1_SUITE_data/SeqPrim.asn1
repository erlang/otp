SeqPrim DEFINITIONS IMPLICIT TAGS ::= 

BEGIN


Seq ::=  SEQUENCE 
{
  bool  BOOLEAN,
  boolCon [20] BOOLEAN,
  boolPri [PRIVATE 21] BOOLEAN,
  boolApp  [APPLICATION 22] BOOLEAN,
  boolExpCon [30] EXPLICIT BOOLEAN,
  boolExpPri [PRIVATE 31] EXPLICIT BOOLEAN,
  boolExpApp  [APPLICATION 32] EXPLICIT BOOLEAN
}

Empty ::= SEQUENCE {}

Big ::= SEQUENCE {
  ...,
  os1 [1] OCTET STRING (SIZE (120..130)) OPTIONAL,
  os2 [2] OCTET STRING (SIZE (128..256)) OPTIONAL,
  os3 [3] OCTET STRING (SIZE (17000..30000)) OPTIONAL
}

END
