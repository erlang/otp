Opt DEFINITIONS IMPLICIT TAGS ::= 

BEGIN

Opt1 ::=  SEQUENCE 
{
  bool0 [0] BOOLEAN,
  bool1 [1] BOOLEAN OPTIONAL,
  bool2 [2] BOOLEAN OPTIONAL,
  bool3 [3] BOOLEAN OPTIONAL
}


Opt2 ::=  SEQUENCE 
{
  bool10 [10] BOOLEAN,
  bool11 [11] BOOLEAN OPTIONAL,
  bool12 [12] BOOLEAN OPTIONAL,
  bool13 [13] BOOLEAN 
}


Opt3 ::=  SEQUENCE 
{
  bool30 [30] BOOLEAN OPTIONAL,
  bool31 [31] BOOLEAN OPTIONAL,
  bool32 [32] BOOLEAN OPTIONAL,
  bool33 [33] BOOLEAN OPTIONAL 
}

END
