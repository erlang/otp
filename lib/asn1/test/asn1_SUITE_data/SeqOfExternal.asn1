SeqOfExternal DEFINITIONS IMPLICIT TAGS ::= 

BEGIN

IMPORTS XSeqNT, XSeqImp, XSeqExp FROM External;


NT ::= SEQUENCE {
  os  OCTET STRING,
  bool  BOOLEAN}
Imp ::= [21] SEQUENCE {
  os  OCTET STRING,
  bool  BOOLEAN}
Exp ::= [22] EXPLICIT SEQUENCE {
  os  OCTET STRING,
  bool  BOOLEAN}

NTNT ::= SEQUENCE OF NT
ImpNT ::= [3] SEQUENCE OF NT
ExpNT ::= [4] EXPLICIT SEQUENCE OF NT

NTImp ::= SEQUENCE OF Imp
ImpImp ::= [5] SEQUENCE OF Imp
ExpImp ::= [6] EXPLICIT SEQUENCE OF Imp

NTExp ::= SEQUENCE OF Exp
ImpExp ::= [7] SEQUENCE OF Exp
ExpExp ::= [8] EXPLICIT SEQUENCE OF Exp

XNTNT ::= SEQUENCE OF XSeqNT
XImpNT ::= [3] SEQUENCE OF XSeqNT
XExpNT ::= [4] EXPLICIT SEQUENCE OF XSeqNT

XNTImp ::= SEQUENCE OF XSeqImp
XImpImp ::= [5] SEQUENCE OF XSeqImp
XExpImp ::= [6] EXPLICIT SEQUENCE OF XSeqImp

XNTExp ::= SEQUENCE OF XSeqExp
XImpExp ::= [7] SEQUENCE OF XSeqExp
XExpExp ::= [8] EXPLICIT SEQUENCE OF XSeqExp

END
