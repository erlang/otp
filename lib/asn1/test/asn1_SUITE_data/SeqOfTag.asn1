SeqOfTag DEFINITIONS IMPLICIT TAGS ::= 

BEGIN

IMPORTS XSeqNT, XSeqImp, XSeqExp FROM External;

SeqTagNt ::= [APPLICATION 20] SEQUENCE {
	nt SEQUENCE OF NT}

SeqTagNtI ::= [APPLICATION 20] SEQUENCE {
	imp SEQUENCE OF Imp}

SeqTagNtE ::= [APPLICATION 20] SEQUENCE {
	exp SEQUENCE OF Exp }

SeqTagI ::= [APPLICATION 21] SEQUENCE {
	nt [0] SEQUENCE OF NT}

SeqTagII ::= [APPLICATION 21] SEQUENCE {
	imp [1] SEQUENCE OF Imp}

SeqTagIE ::= [APPLICATION 21] SEQUENCE {
	exp [2] SEQUENCE OF Exp}

SeqTagE ::= [APPLICATION 22] SEQUENCE {
	nt [0] EXPLICIT SEQUENCE OF NT}

SeqTagEI ::= [APPLICATION 22] SEQUENCE {
	imp [1] EXPLICIT SEQUENCE OF Imp}

SeqTagEE ::= [APPLICATION 22] SEQUENCE {
	exp [2] EXPLICIT SEQUENCE OF Exp}

SeqTagXNt ::= [APPLICATION 30] SEQUENCE {
	xnt SEQUENCE OF XSeqNT}

SeqTagXI ::= [APPLICATION 30] SEQUENCE {
	ximp SEQUENCE OF XSeqImp}

SeqTagXE ::= [APPLICATION 30] SEQUENCE {
	xexp SEQUENCE OF XSeqExp }

SeqTagImpX ::= [APPLICATION 31] SEQUENCE {
	xnt [3] SEQUENCE OF XSeqNT,
	ximp [4] SEQUENCE OF XSeqImp,
	xexp [5] SEQUENCE OF XSeqExp }

SeqTagExpX ::= [APPLICATION 32] SEQUENCE {
	xnt [3] EXPLICIT SEQUENCE OF XSeqNT,
	ximp [4] EXPLICIT SEQUENCE OF XSeqImp,
	xexp [5] EXPLICIT SEQUENCE OF XSeqExp }



NT ::= SEQUENCE {
  os  OCTET STRING,
  bool  BOOLEAN}
Imp ::= [21] SEQUENCE {
  os  OCTET STRING,
  bool  BOOLEAN}
Exp ::= [22] EXPLICIT SEQUENCE {
  os  OCTET STRING,
  bool  BOOLEAN}

END
