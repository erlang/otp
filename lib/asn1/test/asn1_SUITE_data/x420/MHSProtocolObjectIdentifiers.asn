-- Module MHSProtocolObjectIdentifiers (X.419:06/1999)

MHSProtocolObjectIdentifiers {joint-iso-itu-t mhs(6) protocols(0) modules(0)
  object-identifiers(0) version-1994(0)} DEFINITIONS IMPLICIT TAGS ::=
BEGIN

--	Prologue
--	Exports Everything
IMPORTS -- nothing -- ;

ID ::= OBJECT IDENTIFIER

--	MHS Protocols
id-mhs-protocols ID ::=
  {joint-iso-itu-t mhs(6) protocols(0)} -- not definitive

--	Categories of Object Identifiers
id-mod ID ::=
  {id-mhs-protocols  0} -- modules

id-ac ID ::= {id-mhs-protocols  1} -- application contexts

id-as ID ::= {id-mhs-protocols  2} -- abstract syntaxes

id-ase ID ::= {id-mhs-protocols  3} -- application service elements (obsolete)

--	Modules
id-mod-object-identifiers ID ::= {id-mod  0} -- not definitive

id-mod-mts-access-protocol ID ::= {id-mod  1} -- not definitive

id-mod-ms-access-protocol ID ::= {id-mod  2} -- not definitive

id-mod-mts-transfer-protocol ID ::= {id-mod  3} -- not definitive

--	Application Contexts
--	MTS Access Protocol
id-ac-mts-access-88 ID ::=
  {id-ac  0}

id-ac-mts-forced-access-88 ID ::= {id-ac  1}

id-ac-mts-reliable-access-88 ID ::= {id-ac  2}

id-ac-mts-forced-reliable-access-88 ID ::= {id-ac  3}

id-ac-mts-access-94 ID ::= {id-ac  7}

id-ac-mts-forced-access-94 ID ::= {id-ac  8}

id-ac-mts-reliable-access-94 ID ::= {id-ac  9}

id-ac-mts-forced-reliable-access-94 ID ::= {id-ac  10}

--	MS Access Protocol
id-ac-ms-access-88 ID ::= {id-ac  4}

id-ac-ms-reliable-access-88 ID ::= {id-ac  5}

id-ac-ms-access-94 ID ::= {id-ac  11}

id-ac-ms-reliable-access-94 ID ::= {id-ac  12}

--	MTS Transfer Protocol
id-ac-mts-transfer ID ::= {id-ac  6}

--	Abstract Syntaxes
id-as-msse ID ::= {id-as  1}

id-as-mdse-88 ID ::= {id-as  2}

id-as-mrse-88 ID ::= {id-as  5}

id-as-mase-88 ID ::= {id-as  6}

id-as-mtse ID ::= {id-as  7}

id-as-mts-rtse ID ::= {id-as  8}

id-as-ms-88 ID ::= {id-as  9}

id-as-ms-rtse ID ::= {id-as  10}

id-as-mts ID ::= {id-as  11}

id-as-mta-rtse ID ::= {id-as  12}

id-as-ms-msse ID ::= {id-as  13}

id-as-mdse-94 ID ::= {id-as  14}

id-as-mrse-94 ID ::= {id-as  15}

id-as-mase-94 ID ::= {id-as  16}

id-as-ms-94 ID ::= {id-as  17}

--	Application Service Elements
id-ase-msse ID ::= {id-ase  0}

id-ase-mdse ID ::= {id-ase  1}

id-ase-mrse ID ::= {id-ase  2}

id-ase-mase ID ::= {id-ase  3}

id-ase-mtse ID ::= {id-ase  4}

END --of MHSProtocolObjectIdentifiers

-- Generated by Asnp, the ASN.1 pretty-printer of France Telecom R&D
