SeqTypeRefPrim DEFINITIONS IMPLICIT TAGS ::= 

BEGIN


SeqTR ::=  SEQUENCE 
{
  octStr OctStr,
  octStrI [114] OctStr,
  octStrE [115] EXPLICIT OctStr,

  octStr-I OctStrImp,
  octStrI-I [214] OctStrImp,
  octStrE-I [215] EXPLICIT OctStrImp,

  octStr-E OctStrExp,
  octStrI-E [314] OctStrExp,
  octStrE-E [315] EXPLICIT OctStrExp

}

OctStr ::= OCTET STRING
OctStrImp ::= [14] OCTET STRING
OctStrExp ::= [15] EXPLICIT OCTET STRING

-- Types to test {Type,Value} notation, see OTP-4057

Int ::= INTEGER
Bool ::= BOOLEAN
Enum ::= ENUMERATED {a(0),b(1),c(2)}
BitStr ::= BIT STRING
Null ::= NULL
OId ::= OBJECT IDENTIFIER
VStr ::= VisibleString

Seq ::=  SEQUENCE {
  octstr OctStr,
  int Int,
  bool Bool,
  enum Enum,
  bitstr   BitStr,
  null Null,
  oid  OId,
  vstr VStr
}


END
