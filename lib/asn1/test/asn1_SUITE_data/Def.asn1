Def DEFINITIONS IMPLICIT TAGS ::= 

BEGIN

Def1 ::=  SEQUENCE 
{
  bool0 [0] BOOLEAN,
  bool1 [1] BOOLEAN DEFAULT FALSE,
  bool2 [2] BOOLEAN DEFAULT FALSE,
  bool3 [3] BOOLEAN DEFAULT FALSE
}


Def2 ::=  SEQUENCE 
{
  bool10 [10] BOOLEAN,
  bool11 [11] BOOLEAN DEFAULT FALSE,
  bool12 [12] BOOLEAN DEFAULT FALSE,
  bool13 [13] BOOLEAN 
}


Def3 ::=  SEQUENCE 
{
  bool30 [30] BOOLEAN DEFAULT FALSE,
  bool31 [31] BOOLEAN DEFAULT FALSE,
  bool32 [32] BOOLEAN DEFAULT FALSE,
  bool33 [33] BOOLEAN DEFAULT FALSE 
}

END
