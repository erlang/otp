-- **************************************************************
--
-- Constant definitions
--
-- **************************************************************

NBAP-Constants {
itu-t (0) identified-organization (4) etsi (0) mobileDomain (0) 
umts-Access (20) modules (3) nbap (2) version1 (1) nbap-Constants (4)}

DEFINITIONS AUTOMATIC TAGS ::= 

BEGIN

IMPORTS
	ProcedureCode,
	ProtocolIE-ID
FROM NBAP-CommonDataTypes;

-- **************************************************************
--
-- Elementary Procedures
--
-- **************************************************************

id-audit 												ProcedureCode ::= 0
id-auditRequired 										ProcedureCode ::= 1
id-blockResource 										ProcedureCode ::= 2
id-cellDeletion 										ProcedureCode ::= 3
id-cellReconfiguration 									ProcedureCode ::= 4
id-cellSetup 											ProcedureCode ::= 5
id-cellSynchronisationInitiation						ProcedureCode ::= 45
id-cellSynchronisationReconfiguration					ProcedureCode ::= 46
id-cellSynchronisationReporting							ProcedureCode ::= 47
id-cellSynchronisationTermination						ProcedureCode ::= 48
id-cellSynchronisationFailure							ProcedureCode ::= 49
id-commonMeasurementFailure 							ProcedureCode ::= 6
id-commonMeasurementInitiation 							ProcedureCode ::= 7
id-commonMeasurementReport 								ProcedureCode ::= 8
id-commonMeasurementTermination 						ProcedureCode ::= 9
id-commonTransportChannelDelete 						ProcedureCode ::= 10
id-commonTransportChannelReconfigure 					ProcedureCode ::= 11
id-commonTransportChannelSetup 							ProcedureCode ::= 12
id-compressedModeCommand 								ProcedureCode ::= 14
id-dedicatedMeasurementFailure 							ProcedureCode ::= 16
id-dedicatedMeasurementInitiation 						ProcedureCode ::= 17
id-dedicatedMeasurementReport 							ProcedureCode ::= 18
id-dedicatedMeasurementTermination 						ProcedureCode ::= 19
id-downlinkPowerControl 								ProcedureCode ::= 20
id-downlinkPowerTimeslotControl 						ProcedureCode ::= 38
id-errorIndicationForCommon								ProcedureCode ::= 35
id-errorIndicationForDedicated							ProcedureCode ::= 21
id-informationExchangeFailure							ProcedureCode ::= 40
id-informationExchangeInitiation						ProcedureCode ::= 41
id-informationExchangeTermination						ProcedureCode ::= 42
id-informationReporting									ProcedureCode ::= 43
id-BearerRearrangement									ProcedureCode ::= 50
id-physicalSharedChannelReconfiguration 				ProcedureCode ::= 37
id-privateMessageForCommon								ProcedureCode ::= 36
id-privateMessageForDedicated							ProcedureCode ::= 22
id-radioLinkAddition 									ProcedureCode ::= 23
id-radioLinkDeletion 									ProcedureCode ::= 24
id-radioLinkFailure 									ProcedureCode ::= 25
id-radioLinkPreemption									ProcedureCode ::= 39
id-radioLinkRestoration 								ProcedureCode ::= 26
id-radioLinkSetup 										ProcedureCode ::= 27
id-reset												ProcedureCode ::= 13
id-resourceStatusIndication 							ProcedureCode ::= 28
id-cellSynchronisationAdjustment						ProcedureCode ::= 44
id-synchronisedRadioLinkReconfigurationCancellation		ProcedureCode ::= 29
id-synchronisedRadioLinkReconfigurationCommit			ProcedureCode ::= 30
id-synchronisedRadioLinkReconfigurationPreparation 		ProcedureCode ::= 31
id-systemInformationUpdate 								ProcedureCode ::= 32
id-unblockResource 										ProcedureCode ::= 33
id-unSynchronisedRadioLinkReconfiguration 				ProcedureCode ::= 34
id-radioLinkActivation									ProcedureCode ::= 51
id-radioLinkParameterUpdate								ProcedureCode ::= 52

-- **************************************************************
--
-- Lists
--
-- **************************************************************

maxNrOfCodes				INTEGER ::= 10
maxNrOfDLTSs				INTEGER ::= 15
maxNrOfDLTSLCRs				INTEGER ::= 6
maxNrOfErrors				INTEGER ::= 256
maxNrOfTFs					INTEGER ::= 32
maxNrOfTFCs					INTEGER ::= 1024
maxNrOfRLs					INTEGER ::= 16
maxNrOfRLs-1				INTEGER ::= 15	-- maxNrOfRLs - 1
maxNrOfRLs-2				INTEGER ::= 14	-- maxNrOfRLs - 2
maxNrOfRLSets				INTEGER ::= maxNrOfRLs
maxNrOfDPCHs				INTEGER ::= 240
maxNrOfDPCHLCRs				INTEGER ::= 240
maxNrOfSCCPCHs				INTEGER ::= 8
maxNrOfCPCHs				INTEGER ::= 16
maxNrOfPCPCHs				INTEGER ::= 64
maxNrOfDCHs					INTEGER ::= 128
maxNrOfDSCHs				INTEGER ::= 32
maxNrOfFACHs				INTEGER ::= 8
maxNrOfCCTrCHs				INTEGER ::= 16
maxNrOfPDSCHs				INTEGER ::= 256
maxNrOfHSPDSCHs				INTEGER ::= 16
maxNrOfPUSCHs				INTEGER ::= 256
maxNrOfPDSCHSets			INTEGER ::= 256
maxNrOfPRACHLCRs			INTEGER ::= 8
maxNrOfPUSCHSets			INTEGER ::= 256
maxNrOfSCCPCHLCRs			INTEGER ::= 8
maxNrOfULTSs				INTEGER ::= 15
maxNrOfULTSLCRs				INTEGER ::= 6
maxNrOfUSCHs				INTEGER ::= 32
maxAPSigNum					INTEGER ::= 16
maxNrOfSlotFormatsPRACH		INTEGER ::= 8
maxCellinNodeB				INTEGER ::= 256
maxCCPinNodeB				INTEGER ::= 256
maxCPCHCell					INTEGER ::= maxNrOfCPCHs
maxCTFC						INTEGER ::= 16777215
maxLocalCellinNodeB			INTEGER ::= maxCellinNodeB
maxNoofLen					INTEGER ::= 7
maxFPACHCell				INTEGER ::= 8
maxRACHCell					INTEGER ::= maxPRACHCell
maxPRACHCell				INTEGER ::= 16
maxPCPCHCell				INTEGER ::= 64
maxSCCPCHCell				INTEGER ::= 32
maxSCPICHCell				INTEGER ::= 32
maxTTI-count				INTEGER ::= 4
maxIBSEG					INTEGER ::= 16
maxIB						INTEGER ::= 64
maxFACHCell 				INTEGER ::= 256	-- maxNrOfFACHs * maxSCCPCHCell
maxRateMatching				INTEGER ::= 256
maxCodeNrComp-1				INTEGER ::= 256
maxHS-PDSCHCodeNrComp-1		INTEGER ::= 15
maxHS-SCCHCodeNrComp-1		INTEGER ::= 127
maxNrOfCellSyncBursts		INTEGER ::= 10
maxNrOfCodeGroups			INTEGER ::= 256
maxNrOfReceptsPerSyncFrame	INTEGER ::= 16
maxNrOfMeasNCell			INTEGER ::= 96
maxNrOfMeasNCell-1			INTEGER ::= 95	-- maxNrOfMeasNCell - 1
maxNrOfTFCIGroups			INTEGER ::= 256
maxNrOfTFCI1Combs			INTEGER ::= 512
maxNrOfTFCI2Combs			INTEGER ::= 1024
maxNrOfTFCI2Combs-1			INTEGER ::= 1023
maxNrOfSF					INTEGER ::= 8
maxTGPS						INTEGER ::= 6
maxCommunicationContext		INTEGER ::= 1048575
maxNrOfLevels				INTEGER ::= 256
maxNoSat					INTEGER ::= 16
maxNoGPSItems				INTEGER ::= 8
maxNrOfHSSCCHs				INTEGER ::= 32
maxNrOfHSSICHs				INTEGER ::= 4
maxNrOfSyncFramesLCR		INTEGER ::= 512
maxNrOfReceptionsperSyncFrameLCR	INTEGER ::=	8
maxNrOfSyncDLCodesLCR		INTEGER ::= 32
maxNrOfHSSCCHCodes			INTEGER ::= 4
maxNrOfMACdFlows			INTEGER ::= 8
maxNrOfMACdFlows-1			INTEGER ::= 7	-- maxNrOfMACdFlows - 1
maxNrOfMACdPDUIndexes		INTEGER ::= 8
maxNrOfMACdPDUIndexes-1		INTEGER ::= 7	-- maxNoOfMACdPDUIndexes - 1
maxNrOfPriorityQueues		INTEGER ::= 8
maxNrOfPriorityQueues-1		INTEGER ::= 7	-- maxNoOfPriorityQueues - 1
maxNrOfHARQProcesses		INTEGER ::= 8
maxNrOfContextsOnUeList		INTEGER ::= 16
maxNrOfCellPortionsPerCell		INTEGER ::= 64
maxNrOfCellPortionsPerCell-1	INTEGER ::= 63
maxNrOfPriorityClasses			INTEGER ::= 16
maxNrOfSatAlmanac-maxNoSat		INTEGER ::= 16  -- maxNrofSatAlmanac - maxNoSat


-- **************************************************************
--
-- IEs
--
-- **************************************************************

id-AICH-Information													ProtocolIE-ID ::= 0
id-AICH-InformationItem-ResourceStatusInd							ProtocolIE-ID ::= 1
id-BCH-Information													ProtocolIE-ID ::= 7
id-BCH-InformationItem-ResourceStatusInd							ProtocolIE-ID ::= 8
id-BCCH-ModificationTime											ProtocolIE-ID ::= 9
id-BlockingPriorityIndicator										ProtocolIE-ID ::= 10
id-Cause															ProtocolIE-ID ::= 13
id-CCP-InformationItem-AuditRsp										ProtocolIE-ID ::= 14
id-CCP-InformationList-AuditRsp										ProtocolIE-ID ::= 15
id-CCP-InformationItem-ResourceStatusInd							ProtocolIE-ID ::= 16
id-Cell-InformationItem-AuditRsp									ProtocolIE-ID ::= 17
id-Cell-InformationItem-ResourceStatusInd							ProtocolIE-ID ::= 18
id-Cell-InformationList-AuditRsp									ProtocolIE-ID ::= 19
id-CellParameterID													ProtocolIE-ID ::= 23
id-CFN																ProtocolIE-ID ::= 24
id-C-ID																	ProtocolIE-ID ::= 25
id-CommonMeasurementAccuracy										ProtocolIE-ID ::= 39
id-CommonMeasurementObjectType-CM-Rprt								ProtocolIE-ID ::= 31
id-CommonMeasurementObjectType-CM-Rqst								ProtocolIE-ID ::= 32
id-CommonMeasurementObjectType-CM-Rsp								ProtocolIE-ID ::= 33
id-CommonMeasurementType											ProtocolIE-ID ::= 34
id-CommonPhysicalChannelID											ProtocolIE-ID ::= 35
id-CommonPhysicalChannelType-CTCH-SetupRqstFDD						ProtocolIE-ID ::= 36
id-CommonPhysicalChannelType-CTCH-SetupRqstTDD						ProtocolIE-ID ::= 37
id-CommunicationControlPortID										ProtocolIE-ID ::= 40
id-ConfigurationGenerationID										ProtocolIE-ID ::= 43
id-CRNC-CommunicationContextID										ProtocolIE-ID ::= 44
id-CriticalityDiagnostics											ProtocolIE-ID ::= 45
id-DCHs-to-Add-FDD													ProtocolIE-ID ::= 48
id-DCH-AddList-RL-ReconfPrepTDD										ProtocolIE-ID ::= 49
id-DCHs-to-Add-TDD													ProtocolIE-ID ::= 50
id-DCH-DeleteList-RL-ReconfPrepFDD									ProtocolIE-ID ::= 52
id-DCH-DeleteList-RL-ReconfPrepTDD									ProtocolIE-ID ::= 53
id-DCH-DeleteList-RL-ReconfRqstFDD									ProtocolIE-ID ::= 54
id-DCH-DeleteList-RL-ReconfRqstTDD									ProtocolIE-ID ::= 55
id-DCH-FDD-Information												ProtocolIE-ID ::= 56
id-DCH-TDD-Information												ProtocolIE-ID ::= 57
id-DCH-InformationResponse											ProtocolIE-ID ::= 59
id-FDD-DCHs-to-Modify												ProtocolIE-ID ::= 62
id-TDD-DCHs-to-Modify												ProtocolIE-ID ::= 63
id-DCH-ModifyList-RL-ReconfRqstTDD									ProtocolIE-ID ::= 65
id-DCH-RearrangeList-Bearer-RearrangeInd							ProtocolIE-ID ::= 135
id-DedicatedMeasurementObjectType-DM-Rprt							ProtocolIE-ID ::= 67
id-DedicatedMeasurementObjectType-DM-Rqst							ProtocolIE-ID ::= 68
id-DedicatedMeasurementObjectType-DM-Rsp							ProtocolIE-ID ::= 69
id-DedicatedMeasurementType											ProtocolIE-ID ::= 70
id-DL-CCTrCH-InformationItem-RL-SetupRqstTDD						ProtocolIE-ID ::= 72
id-DL-CCTrCH-InformationList-RL-AdditionRqstTDD						ProtocolIE-ID ::= 73
id-DL-CCTrCH-InformationList-RL-SetupRqstTDD						ProtocolIE-ID ::= 76
id-DL-DPCH-InformationItem-RL-AdditionRqstTDD						ProtocolIE-ID ::= 77
id-DL-DPCH-InformationList-RL-SetupRqstTDD							ProtocolIE-ID ::= 79
id-DL-DPCH-Information-RL-ReconfPrepFDD								ProtocolIE-ID ::= 81
id-DL-DPCH-Information-RL-ReconfRqstFDD								ProtocolIE-ID ::= 82
id-DL-DPCH-Information-RL-SetupRqstFDD								ProtocolIE-ID ::= 83
id-DL-DPCH-TimingAdjustment											ProtocolIE-ID ::= 21
id-DL-ReferencePowerInformationItem-DL-PC-Rqst						ProtocolIE-ID ::= 84
id-DLReferencePower													ProtocolIE-ID ::= 85
id-DLReferencePowerList-DL-PC-Rqst									ProtocolIE-ID ::= 86
id-DSCH-AddItem-RL-ReconfPrepFDD									ProtocolIE-ID ::= 87
id-DSCHs-to-Add-FDD													ProtocolIE-ID ::= 89
id-DSCH-DeleteItem-RL-ReconfPrepFDD									ProtocolIE-ID ::= 91
id-DSCH-DeleteList-RL-ReconfPrepFDD									ProtocolIE-ID ::= 93
id-DSCHs-to-Add-TDD													ProtocolIE-ID ::= 96
id-DSCH-Information-DeleteList-RL-ReconfPrepTDD						ProtocolIE-ID ::= 98
id-DSCH-Information-ModifyList-RL-ReconfPrepTDD						ProtocolIE-ID ::= 100
id-DSCH-InformationResponse											ProtocolIE-ID ::= 105
id-DSCH-FDD-Information												ProtocolIE-ID ::= 106
id-DSCH-TDD-Information												ProtocolIE-ID ::= 107
id-DSCH-ModifyItem-RL-ReconfPrepFDD									ProtocolIE-ID ::= 108
id-DSCH-ModifyList-RL-ReconfPrepFDD									ProtocolIE-ID ::= 112
id-DSCH-RearrangeList-Bearer-RearrangeInd							ProtocolIE-ID ::= 136
id-End-Of-Audit-Sequence-Indicator 									ProtocolIE-ID ::= 113
id-FACH-Information													ProtocolIE-ID ::= 116
id-FACH-InformationItem-ResourceStatusInd							ProtocolIE-ID ::= 117
id-FACH-ParametersList-CTCH-ReconfRqstTDD							ProtocolIE-ID ::= 120
id-FACH-ParametersListIE-CTCH-SetupRqstFDD							ProtocolIE-ID ::= 121
id-FACH-ParametersListIE-CTCH-SetupRqstTDD							ProtocolIE-ID ::= 122
id-IndicationType-ResourceStatusInd									ProtocolIE-ID ::= 123
id-Local-Cell-ID													ProtocolIE-ID ::= 124
id-Local-Cell-Group-InformationItem-AuditRsp						ProtocolIE-ID ::= 2
id-Local-Cell-Group-InformationItem-ResourceStatusInd				ProtocolIE-ID ::= 3
id-Local-Cell-Group-InformationItem2-ResourceStatusInd				ProtocolIE-ID ::= 4
id-Local-Cell-Group-InformationList-AuditRsp						ProtocolIE-ID ::= 5
id-Local-Cell-InformationItem-AuditRsp								ProtocolIE-ID ::= 125
id-Local-Cell-InformationItem-ResourceStatusInd						ProtocolIE-ID ::= 126
id-Local-Cell-InformationItem2-ResourceStatusInd					ProtocolIE-ID ::= 127
id-Local-Cell-InformationList-AuditRsp								ProtocolIE-ID ::= 128
id-AdjustmentPeriod													ProtocolIE-ID ::= 129
id-MaxAdjustmentStep												ProtocolIE-ID ::= 130
id-MaximumTransmissionPower											ProtocolIE-ID ::= 131
id-MeasurementFilterCoefficient										ProtocolIE-ID ::= 132
id-MeasurementID													ProtocolIE-ID ::= 133
id-MessageStructure													ProtocolIE-ID ::= 115
id-MIB-SB-SIB-InformationList-SystemInfoUpdateRqst					ProtocolIE-ID ::= 134
id-NodeB-CommunicationContextID										ProtocolIE-ID ::= 143
id-NeighbouringCellMeasurementInformation							ProtocolIE-ID ::= 455
id-P-CCPCH-Information												ProtocolIE-ID ::= 144
id-P-CCPCH-InformationItem-ResourceStatusInd						ProtocolIE-ID ::= 145
id-P-CPICH-Information												ProtocolIE-ID ::= 146
id-P-CPICH-InformationItem-ResourceStatusInd						ProtocolIE-ID ::= 147
id-P-SCH-Information												ProtocolIE-ID ::= 148
id-PCCPCH-Information-Cell-ReconfRqstTDD							ProtocolIE-ID ::= 150
id-PCCPCH-Information-Cell-SetupRqstTDD								ProtocolIE-ID ::= 151
id-PCH-Parameters-CTCH-ReconfRqstTDD								ProtocolIE-ID ::= 155
id-PCH-ParametersItem-CTCH-SetupRqstFDD								ProtocolIE-ID ::= 156
id-PCH-ParametersItem-CTCH-SetupRqstTDD								ProtocolIE-ID ::= 157
id-PCH-Information													ProtocolIE-ID ::= 158
id-PDSCH-Information-AddListIE-PSCH-ReconfRqst						ProtocolIE-ID ::= 161
id-PDSCH-Information-ModifyListIE-PSCH-ReconfRqst					ProtocolIE-ID ::= 162
id-PDSCHSets-AddList-PSCH-ReconfRqst								ProtocolIE-ID ::= 163
id-PDSCHSets-DeleteList-PSCH-ReconfRqst								ProtocolIE-ID ::= 164
id-PDSCHSets-ModifyList-PSCH-ReconfRqst								ProtocolIE-ID ::= 165
id-PICH-Information													ProtocolIE-ID ::= 166
id-PICH-Parameters-CTCH-ReconfRqstTDD								ProtocolIE-ID ::= 168
id-PowerAdjustmentType												ProtocolIE-ID ::= 169
id-PRACH-Information												ProtocolIE-ID ::= 170
id-PrimaryCCPCH-Information-Cell-ReconfRqstFDD						ProtocolIE-ID ::= 175
id-PrimaryCCPCH-Information-Cell-SetupRqstFDD						ProtocolIE-ID ::= 176
id-PrimaryCPICH-Information-Cell-ReconfRqstFDD						ProtocolIE-ID ::= 177
id-PrimaryCPICH-Information-Cell-SetupRqstFDD						ProtocolIE-ID ::= 178
id-PrimarySCH-Information-Cell-ReconfRqstFDD						ProtocolIE-ID ::= 179
id-PrimarySCH-Information-Cell-SetupRqstFDD							ProtocolIE-ID ::= 180
id-PrimaryScramblingCode											ProtocolIE-ID ::= 181
id-SCH-Information-Cell-ReconfRqstTDD								ProtocolIE-ID ::= 183
id-SCH-Information-Cell-SetupRqstTDD								ProtocolIE-ID ::= 184
id-PUSCH-Information-AddListIE-PSCH-ReconfRqst						ProtocolIE-ID ::= 185
id-PUSCH-Information-ModifyListIE-PSCH-ReconfRqst					ProtocolIE-ID ::= 186
id-PUSCHSets-AddList-PSCH-ReconfRqst								ProtocolIE-ID ::= 187
id-PUSCHSets-DeleteList-PSCH-ReconfRqst								ProtocolIE-ID ::= 188
id-PUSCHSets-ModifyList-PSCH-ReconfRqst								ProtocolIE-ID ::= 189
id-RACH-Information													ProtocolIE-ID ::= 190
id-RACH-ParametersItem-CTCH-SetupRqstFDD							ProtocolIE-ID ::= 196
id-RACH-ParameterItem-CTCH-SetupRqstTDD								ProtocolIE-ID ::= 197
id-ReportCharacteristics											ProtocolIE-ID ::= 198
id-Reporting-Object-RL-FailureInd									ProtocolIE-ID ::= 199
id-Reporting-Object-RL-RestoreInd									ProtocolIE-ID ::= 200
id-RL-InformationItem-DM-Rprt										ProtocolIE-ID ::= 202
id-RL-InformationItem-DM-Rqst										ProtocolIE-ID ::= 203
id-RL-InformationItem-DM-Rsp										ProtocolIE-ID ::= 204
id-RL-InformationItem-RL-AdditionRqstFDD							ProtocolIE-ID ::= 205
id-RL-informationItem-RL-DeletionRqst								ProtocolIE-ID ::= 206
id-RL-InformationItem-RL-FailureInd									ProtocolIE-ID ::= 207
id-RL-InformationItem-RL-PreemptRequiredInd							ProtocolIE-ID ::= 286
id-RL-InformationItem-RL-ReconfPrepFDD								ProtocolIE-ID ::= 208
id-RL-InformationItem-RL-ReconfRqstFDD								ProtocolIE-ID ::= 209
id-RL-InformationItem-RL-RestoreInd									ProtocolIE-ID ::= 210
id-RL-InformationItem-RL-SetupRqstFDD								ProtocolIE-ID ::= 211
id-RL-InformationList-RL-AdditionRqstFDD							ProtocolIE-ID ::= 212
id-RL-informationList-RL-DeletionRqst								ProtocolIE-ID ::= 213
id-RL-InformationList-RL-PreemptRequiredInd							ProtocolIE-ID ::= 237
id-RL-InformationList-RL-ReconfPrepFDD								ProtocolIE-ID ::= 214
id-RL-InformationList-RL-ReconfRqstFDD								ProtocolIE-ID ::= 215
id-RL-InformationList-RL-SetupRqstFDD								ProtocolIE-ID ::= 216
id-RL-InformationResponseItem-RL-AdditionRspFDD						ProtocolIE-ID ::= 217
id-RL-InformationResponseItem-RL-ReconfReady						ProtocolIE-ID ::= 218
id-RL-InformationResponseItem-RL-ReconfRsp							ProtocolIE-ID ::= 219
id-RL-InformationResponseItem-RL-SetupRspFDD						ProtocolIE-ID ::= 220
id-RL-InformationResponseList-RL-AdditionRspFDD						ProtocolIE-ID ::= 221
id-RL-InformationResponseList-RL-ReconfReady						ProtocolIE-ID ::= 222
id-RL-InformationResponseList-RL-ReconfRsp							ProtocolIE-ID ::= 223
id-RL-InformationResponseList-RL-SetupRspFDD						ProtocolIE-ID ::= 224
id-RL-InformationResponse-RL-AdditionRspTDD							ProtocolIE-ID ::= 225
id-RL-InformationResponse-RL-SetupRspTDD							ProtocolIE-ID ::= 226
id-RL-Information-RL-AdditionRqstTDD								ProtocolIE-ID ::= 227
id-RL-Information-RL-ReconfRqstTDD									ProtocolIE-ID ::= 228
id-RL-Information-RL-ReconfPrepTDD									ProtocolIE-ID ::= 229
id-RL-Information-RL-SetupRqstTDD									ProtocolIE-ID ::= 230
id-RL-ReconfigurationFailureItem-RL-ReconfFailure					ProtocolIE-ID ::= 236
id-RL-Set-InformationItem-DM-Rprt									ProtocolIE-ID ::= 238
id-RL-Set-InformationItem-DM-Rsp									ProtocolIE-ID ::= 240
id-RL-Set-InformationItem-RL-FailureInd								ProtocolIE-ID ::= 241
id-RL-Set-InformationItem-RL-RestoreInd								ProtocolIE-ID ::= 242
id-S-CCPCH-Information												ProtocolIE-ID ::= 247
id-S-CPICH-Information												ProtocolIE-ID ::= 249
id-SCH-Information													ProtocolIE-ID ::= 251
id-S-SCH-Information												ProtocolIE-ID ::= 253
id-Secondary-CCPCHListIE-CTCH-ReconfRqstTDD							ProtocolIE-ID ::= 257
id-Secondary-CCPCH-parameterListIE-CTCH-SetupRqstTDD				ProtocolIE-ID ::= 258
id-Secondary-CCPCH-Parameters-CTCH-ReconfRqstTDD					ProtocolIE-ID ::= 259
id-SecondaryCPICH-InformationItem-Cell-ReconfRqstFDD				ProtocolIE-ID ::= 260
id-SecondaryCPICH-InformationItem-Cell-SetupRqstFDD					ProtocolIE-ID ::= 261
id-SecondaryCPICH-InformationList-Cell-ReconfRqstFDD				ProtocolIE-ID ::= 262
id-SecondaryCPICH-InformationList-Cell-SetupRqstFDD					ProtocolIE-ID ::= 263
id-SecondarySCH-Information-Cell-ReconfRqstFDD						ProtocolIE-ID ::= 264
id-SecondarySCH-Information-Cell-SetupRqstFDD						ProtocolIE-ID ::= 265
id-SegmentInformationListIE-SystemInfoUpdate						ProtocolIE-ID ::= 266
id-SFN																ProtocolIE-ID ::= 268
id-SignallingBearerRequestIndicator									ProtocolIE-ID ::= 138
id-ShutdownTimer													ProtocolIE-ID ::= 269
id-Start-Of-Audit-Sequence-Indicator								ProtocolIE-ID ::= 114
id-Successful-RL-InformationRespItem-RL-AdditionFailureFDD			ProtocolIE-ID ::= 270
id-Successful-RL-InformationRespItem-RL-SetupFailureFDD				ProtocolIE-ID ::= 271
id-SyncCase															ProtocolIE-ID ::= 274
id-SyncCaseIndicatorItem-Cell-SetupRqstTDD-PSCH						ProtocolIE-ID ::= 275
id-T-Cell															ProtocolIE-ID ::= 276
id-TargetCommunicationControlPortID									ProtocolIE-ID ::= 139
id-TimeSlotConfigurationList-Cell-ReconfRqstTDD						ProtocolIE-ID ::= 277
id-TimeSlotConfigurationList-Cell-SetupRqstTDD						ProtocolIE-ID ::= 278
id-TransmissionDiversityApplied										ProtocolIE-ID ::= 279
id-TypeOfError														ProtocolIE-ID ::= 508
id-UARFCNforNt														ProtocolIE-ID ::= 280
id-UARFCNforNd														ProtocolIE-ID ::= 281
id-UARFCNforNu														ProtocolIE-ID ::= 282
id-UL-CCTrCH-InformationItem-RL-SetupRqstTDD						ProtocolIE-ID ::= 284
id-UL-CCTrCH-InformationList-RL-AdditionRqstTDD						ProtocolIE-ID ::= 285
id-UL-CCTrCH-InformationList-RL-SetupRqstTDD						ProtocolIE-ID ::= 288
id-UL-DPCH-InformationItem-RL-AdditionRqstTDD						ProtocolIE-ID ::= 289
id-UL-DPCH-InformationList-RL-SetupRqstTDD							ProtocolIE-ID ::= 291
id-UL-DPCH-Information-RL-ReconfPrepFDD								ProtocolIE-ID ::= 293
id-UL-DPCH-Information-RL-ReconfRqstFDD								ProtocolIE-ID ::= 294
id-UL-DPCH-Information-RL-SetupRqstFDD								ProtocolIE-ID ::= 295
id-Unsuccessful-RL-InformationRespItem-RL-AdditionFailureFDD		ProtocolIE-ID ::= 296
id-Unsuccessful-RL-InformationRespItem-RL-SetupFailureFDD			ProtocolIE-ID ::= 297
id-Unsuccessful-RL-InformationResp-RL-AdditionFailureTDD			ProtocolIE-ID ::= 300
id-Unsuccessful-RL-InformationResp-RL-SetupFailureTDD				ProtocolIE-ID ::= 301
id-USCH-Information-Add												ProtocolIE-ID ::= 302
id-USCH-Information-DeleteList-RL-ReconfPrepTDD						ProtocolIE-ID ::= 304
id-USCH-Information-ModifyList-RL-ReconfPrepTDD						ProtocolIE-ID ::= 306
id-USCH-InformationResponse											ProtocolIE-ID ::= 309
id-USCH-Information													ProtocolIE-ID ::= 310
id-USCH-RearrangeList-Bearer-RearrangeInd							ProtocolIE-ID ::= 141
id-Active-Pattern-Sequence-Information 								ProtocolIE-ID ::= 315
id-AICH-ParametersListIE-CTCH-ReconfRqstFDD							ProtocolIE-ID ::= 316
id-AdjustmentRatio													ProtocolIE-ID ::= 317
id-AP-AICH-Information												ProtocolIE-ID ::= 320
id-AP-AICH-ParametersListIE-CTCH-ReconfRqstFDD						ProtocolIE-ID ::= 322
id-FACH-ParametersListIE-CTCH-ReconfRqstFDD							ProtocolIE-ID ::= 323
id-CauseLevel-PSCH-ReconfFailure									ProtocolIE-ID ::= 324
id-CauseLevel-RL-AdditionFailureFDD									ProtocolIE-ID ::= 325
id-CauseLevel-RL-AdditionFailureTDD									ProtocolIE-ID ::= 326
id-CauseLevel-RL-ReconfFailure										ProtocolIE-ID ::= 327
id-CauseLevel-RL-SetupFailureFDD									ProtocolIE-ID ::= 328
id-CauseLevel-RL-SetupFailureTDD									ProtocolIE-ID ::= 329
id-CDCA-ICH-Information												ProtocolIE-ID ::= 330
id-CDCA-ICH-ParametersListIE-CTCH-ReconfRqstFDD						ProtocolIE-ID ::= 332
id-Closed-Loop-Timing-Adjustment-Mode								ProtocolIE-ID ::= 333
id-CommonPhysicalChannelType-CTCH-ReconfRqstFDD						ProtocolIE-ID ::= 334
id-Compressed-Mode-Deactivation-Flag								ProtocolIE-ID ::= 335
id-CPCH-Information													ProtocolIE-ID ::= 336
id-CPCH-Parameters-CTCH-SetupRsp									ProtocolIE-ID ::= 342
id-CPCH-ParametersListIE-CTCH-ReconfRqstFDD							ProtocolIE-ID ::= 343
id-DL-CCTrCH-InformationAddList-RL-ReconfPrepTDD					ProtocolIE-ID ::= 346
id-DL-CCTrCH-InformationDeleteItem-RL-ReconfRqstTDD					ProtocolIE-ID ::= 347
id-DL-CCTrCH-InformationDeleteList-RL-ReconfPrepTDD					ProtocolIE-ID ::= 348
id-DL-CCTrCH-InformationDeleteList-RL-ReconfRqstTDD					ProtocolIE-ID ::= 349
id-DL-CCTrCH-InformationModifyItem-RL-ReconfRqstTDD					ProtocolIE-ID ::= 350
id-DL-CCTrCH-InformationModifyList-RL-ReconfPrepTDD					ProtocolIE-ID ::= 351
id-DL-CCTrCH-InformationModifyList-RL-ReconfRqstTDD					ProtocolIE-ID ::= 352
id-DL-DPCH-InformationAddListIE-RL-ReconfPrepTDD					ProtocolIE-ID ::= 353
id-DL-DPCH-InformationModify-AddListIE-RL-ReconfPrepTDD				ProtocolIE-ID ::= 355
id-DL-DPCH-InformationModify-DeleteListIE-RL-ReconfPrepTDD			ProtocolIE-ID ::= 356
id-DL-DPCH-InformationModify-ModifyListIE-RL-ReconfPrepTDD			ProtocolIE-ID ::= 357
id-DL-TPC-Pattern01Count 											ProtocolIE-ID ::= 358
id-DPC-Mode															ProtocolIE-ID ::= 450
id-DPCHConstant														ProtocolIE-ID ::= 359
id-DSCH-FDD-Common-Information										ProtocolIE-ID ::= 94
id-EnhancedDSCHPC													ProtocolIE-ID ::= 110
id-EnhancedDSCHPCIndicator											ProtocolIE-ID ::= 111
id-FACH-ParametersList-CTCH-SetupRsp								ProtocolIE-ID ::= 362
id-Limited-power-increase-information-Cell-SetupRqstFDD				ProtocolIE-ID ::= 369
id-PCH-Parameters-CTCH-SetupRsp										ProtocolIE-ID ::= 374
id-PCH-ParametersItem-CTCH-ReconfRqstFDD							ProtocolIE-ID ::= 375
id-PCPCH-Information 												ProtocolIE-ID ::= 376
id-PICH-ParametersItem-CTCH-ReconfRqstFDD							ProtocolIE-ID ::= 380
id-PRACHConstant													ProtocolIE-ID ::= 381
id-PRACH-ParametersListIE-CTCH-ReconfRqstFDD						ProtocolIE-ID ::= 383
id-PUSCHConstant													ProtocolIE-ID ::= 384
id-RACH-Parameters-CTCH-SetupRsp									ProtocolIE-ID ::= 385
id-SSDT-CellIDforEDSCHPC											ProtocolIE-ID ::= 443
id-Synchronisation-Configuration-Cell-ReconfRqst					ProtocolIE-ID ::= 393
id-Synchronisation-Configuration-Cell-SetupRqst						ProtocolIE-ID ::= 394
id-Transmission-Gap-Pattern-Sequence-Information					ProtocolIE-ID ::= 395
id-UL-CCTrCH-InformationAddList-RL-ReconfPrepTDD					ProtocolIE-ID ::= 396
id-UL-CCTrCH-InformationDeleteItem-RL-ReconfRqstTDD					ProtocolIE-ID ::= 397
id-UL-CCTrCH-InformationDeleteList-RL-ReconfPrepTDD					ProtocolIE-ID ::= 398
id-UL-CCTrCH-InformationDeleteList-RL-ReconfRqstTDD					ProtocolIE-ID ::= 399
id-UL-CCTrCH-InformationModifyItem-RL-ReconfRqstTDD					ProtocolIE-ID ::= 400
id-UL-CCTrCH-InformationModifyList-RL-ReconfPrepTDD					ProtocolIE-ID ::= 401
id-UL-CCTrCH-InformationModifyList-RL-ReconfRqstTDD					ProtocolIE-ID ::= 402
id-UL-DPCH-InformationAddListIE-RL-ReconfPrepTDD					ProtocolIE-ID ::= 403
id-UL-DPCH-InformationModify-AddListIE-RL-ReconfPrepTDD				ProtocolIE-ID ::= 405
id-UL-DPCH-InformationModify-DeleteListIE-RL-ReconfPrepTDD			ProtocolIE-ID ::= 406
id-UL-DPCH-InformationModify-ModifyListIE-RL-ReconfPrepTDD			ProtocolIE-ID ::= 407
id-Unsuccessful-PDSCHSetItem-PSCH-ReconfFailureTDD					ProtocolIE-ID ::= 408
id-Unsuccessful-PUSCHSetItem-PSCH-ReconfFailureTDD					ProtocolIE-ID ::= 409
id-CommunicationContextInfoItem-Reset								ProtocolIE-ID ::= 412
id-CommunicationControlPortInfoItem-Reset							ProtocolIE-ID ::= 414
id-ResetIndicator													ProtocolIE-ID ::= 416
id-TFCI2-Bearer-Information-RL-SetupRqstFDD							ProtocolIE-ID ::= 417
id-TFCI2-BearerSpecificInformation-RL-ReconfPrepFDD					ProtocolIE-ID ::= 418
id-TFCI2-BearerInformationResponse									ProtocolIE-ID ::= 419
id-TFCI2BearerRequestIndicator										ProtocolIE-ID ::= 142
id-TimingAdvanceApplied												ProtocolIE-ID ::= 287
id-CFNReportingIndicator                                            ProtocolIE-ID ::= 6
id-SFNReportingIndicator                                            ProtocolIE-ID ::= 11
id-InnerLoopDLPCStatus												ProtocolIE-ID ::= 12
id-TimeslotISCPInfo													ProtocolIE-ID ::= 283
id-PICH-ParametersItem-CTCH-SetupRqstTDD							ProtocolIE-ID ::= 167
id-PRACH-ParametersItem-CTCH-SetupRqstTDD							ProtocolIE-ID ::= 20
id-CCTrCH-InformationItem-RL-FailureInd								ProtocolIE-ID ::= 46
id-CCTrCH-InformationItem-RL-RestoreInd								ProtocolIE-ID ::= 47
id-CauseLevel-SyncAdjustmntFailureTDD								ProtocolIE-ID ::= 420
id-CellAdjustmentInfo-SyncAdjustmntRqstTDD							ProtocolIE-ID ::= 421
id-CellAdjustmentInfoItem-SyncAdjustmentRqstTDD						ProtocolIE-ID ::= 494
id-CellSyncBurstInfoList-CellSyncReconfRqstTDD						ProtocolIE-ID ::= 482
id-CellSyncBurstTransInit-CellSyncInitiationRqstTDD					ProtocolIE-ID ::= 422
id-CellSyncBurstMeasureInit-CellSyncInitiationRqstTDD				ProtocolIE-ID ::= 423
id-CellSyncBurstTransReconfiguration-CellSyncReconfRqstTDD			ProtocolIE-ID ::= 424
id-CellSyncBurstMeasReconfiguration-CellSyncReconfRqstTDD			ProtocolIE-ID ::= 425
id-CellSyncBurstTransInfoList-CellSyncReconfRqstTDD					ProtocolIE-ID ::= 426
id-CellSyncBurstMeasInfoList-CellSyncReconfRqstTDD					ProtocolIE-ID ::= 427
id-CellSyncBurstTransReconfInfo-CellSyncReconfRqstTDD				ProtocolIE-ID ::= 428
id-CellSyncInfo-CellSyncReprtTDD									ProtocolIE-ID ::= 429
id-CSBTransmissionID												ProtocolIE-ID ::= 430
id-CSBMeasurementID													ProtocolIE-ID ::= 431
id-IntStdPhCellSyncInfoItem-CellSyncReprtTDD						ProtocolIE-ID ::= 432
id-NCyclesPerSFNperiod 												ProtocolIE-ID ::= 433
id-NRepetitionsPerCyclePeriod										ProtocolIE-ID ::= 434
id-SyncFrameNumber													ProtocolIE-ID ::= 437
id-SynchronisationReportType										ProtocolIE-ID ::= 438
id-SynchronisationReportCharacteristics								ProtocolIE-ID ::= 439
id-Unsuccessful-cell-InformationRespItem-SyncAdjustmntFailureTDD	ProtocolIE-ID ::= 440
id-LateEntranceCellSyncInfoItem-CellSyncReprtTDD					ProtocolIE-ID ::= 119
id-ReferenceClockAvailability										ProtocolIE-ID ::= 435
id-ReferenceSFNoffset												ProtocolIE-ID ::= 436
id-InformationExchangeID											ProtocolIE-ID ::= 444
id-InformationExchangeObjectType-InfEx-Rqst							ProtocolIE-ID ::= 445
id-InformationType													ProtocolIE-ID ::= 446
id-InformationReportCharacteristics									ProtocolIE-ID ::= 447
id-InformationExchangeObjectType-InfEx-Rsp							ProtocolIE-ID ::= 448
id-InformationExchangeObjectType-InfEx-Rprt							ProtocolIE-ID ::= 449
id-IPDLParameter-Information-Cell-ReconfRqstFDD						ProtocolIE-ID ::= 451
id-IPDLParameter-Information-Cell-SetupRqstFDD						ProtocolIE-ID ::= 452
id-IPDLParameter-Information-Cell-ReconfRqstTDD						ProtocolIE-ID ::= 453
id-IPDLParameter-Information-Cell-SetupRqstTDD						ProtocolIE-ID ::= 454
id-DL-DPCH-LCR-Information-RL-SetupRqstTDD							ProtocolIE-ID ::= 74
id-DwPCH-LCR-Information											ProtocolIE-ID ::= 78
id-DwPCH-LCR-InformationList-AuditRsp                   			ProtocolIE-ID ::= 90
id-DwPCH-LCR-Information-Cell-SetupRqstTDD                   		ProtocolIE-ID ::= 97
id-DwPCH-LCR-Information-Cell-ReconfRqstTDD							ProtocolIE-ID ::= 99
id-DwPCH-LCR-Information-ResourceStatusInd							ProtocolIE-ID ::= 101
id-maxFACH-Power-LCR-CTCH-SetupRqstTDD                   			ProtocolIE-ID ::= 154
id-maxFACH-Power-LCR-CTCH-ReconfRqstTDD                   			ProtocolIE-ID ::= 174
id-FPACH-LCR-Information											ProtocolIE-ID ::= 290
id-FPACH-LCR-Information-AuditRsp                   				ProtocolIE-ID ::= 292
id-FPACH-LCR-InformationList-AuditRsp                   			ProtocolIE-ID ::= 22
id-FPACH-LCR-InformationList-ResourceStatusInd                   	ProtocolIE-ID ::= 311
id-FPACH-LCR-Parameters-CTCH-SetupRqstTDD                   		ProtocolIE-ID ::= 312
id-FPACH-LCR-Parameters-CTCH-ReconfRqstTDD                   		ProtocolIE-ID ::= 314
id-PCCPCH-LCR-Information-Cell-SetupRqstTDD                   		ProtocolIE-ID ::= 456
id-PCH-Power-LCR-CTCH-SetupRqstTDD									ProtocolIE-ID ::= 457
id-PCH-Power-LCR-CTCH-ReconfRqstTDD									ProtocolIE-ID ::= 458
id-PICH-LCR-Parameters-CTCH-SetupRqstTDD                   			ProtocolIE-ID ::= 459
id-PRACH-LCR-ParametersList-CTCH-SetupRqstTDD                  		ProtocolIE-ID ::= 461
id-RL-InformationResponse-LCR-RL-SetupRspTDD	                   	ProtocolIE-ID ::= 463
id-Secondary-CCPCH-LCR-parameterList-CTCH-SetupRqstTDD              ProtocolIE-ID ::= 465
id-TimeSlot															ProtocolIE-ID ::= 495
id-TimeSlotConfigurationList-LCR-Cell-ReconfRqstTDD                 ProtocolIE-ID ::= 466
id-TimeSlotConfigurationList-LCR-Cell-SetupRqstTDD                  ProtocolIE-ID ::= 467
id-TimeslotISCP-LCR-InfoList-RL-SetupRqstTDD                   		ProtocolIE-ID ::= 468
id-TimeSlotLCR-CM-Rqst                   							ProtocolIE-ID ::= 469
id-UL-DPCH-LCR-Information-RL-SetupRqstTDD                   		ProtocolIE-ID ::= 470
id-DL-DPCH-InformationItem-LCR-RL-AdditionRqstTDD					ProtocolIE-ID ::= 472
id-UL-DPCH-InformationItem-LCR-RL-AdditionRqstTDD					ProtocolIE-ID ::= 473
id-TimeslotISCP-InformationList-LCR-RL-AdditionRqstTDD				ProtocolIE-ID ::= 474
id-DL-DPCH-LCR-InformationAddList-RL-ReconfPrepTDD					ProtocolIE-ID ::= 475
id-DL-DPCH-LCR-InformationModify-AddList-RL-ReconfPrepTDD			ProtocolIE-ID ::= 477
id-DL-Timeslot-LCR-InformationModify-ModifyList-RL-ReconfPrepTDD	ProtocolIE-ID ::= 479
id-TimeslotISCPInfoList-LCR-DL-PC-RqstTDD							ProtocolIE-ID ::= 480
id-UL-DPCH-LCR-InformationAddListIE-RL-ReconfPrepTDD				ProtocolIE-ID ::= 481
id-UL-DPCH-LCR-InformationModify-AddList							ProtocolIE-ID ::= 483
id-UL-TimeslotLCR-Information-RL-ReconfPrepTDD						ProtocolIE-ID ::= 485
id-UL-SIRTarget														ProtocolIE-ID ::= 510
id-PDSCH-AddInformation-LCR-PSCH-ReconfRqst							ProtocolIE-ID ::= 486
id-PDSCH-AddInformation-LCR-AddListIE-PSCH-ReconfRqst				ProtocolIE-ID ::= 487
id-PDSCH-Information-Cell-SetupRqstFDD								ProtocolIE-ID ::=  26
id-PDSCH-Information-Cell-ReconfRqstFDD								ProtocolIE-ID ::=  27
id-PDSCH-ModifyInformation-LCR-PSCH-ReconfRqst						ProtocolIE-ID ::= 488
id-PDSCH-ModifyInformation-LCR-ModifyListIE-PSCH-ReconfRqst			ProtocolIE-ID ::= 489
id-PUSCH-AddInformation-LCR-PSCH-ReconfRqst							ProtocolIE-ID ::= 490
id-PUSCH-AddInformation-LCR-AddListIE-PSCH-ReconfRqst				ProtocolIE-ID ::= 491
id-PUSCH-ModifyInformation-LCR-PSCH-ReconfRqst						ProtocolIE-ID ::= 492
id-PUSCH-ModifyInformation-LCR-ModifyListIE-PSCH-ReconfRqst			ProtocolIE-ID ::= 493
id-timeslotInfo-CellSyncInitiationRqstTDD							ProtocolIE-ID ::= 496
id-SyncReportType-CellSyncReprtTDD									ProtocolIE-ID ::= 497
id-Power-Local-Cell-Group-InformationItem-AuditRsp					ProtocolIE-ID ::= 498
id-Power-Local-Cell-Group-InformationItem-ResourceStatusInd			ProtocolIE-ID ::= 499
id-Power-Local-Cell-Group-InformationItem2-ResourceStatusInd		ProtocolIE-ID ::= 500
id-Power-Local-Cell-Group-InformationList-AuditRsp					ProtocolIE-ID ::= 501
id-Power-Local-Cell-Group-InformationList-ResourceStatusInd			ProtocolIE-ID ::= 502
id-Power-Local-Cell-Group-InformationList2-ResourceStatusInd		ProtocolIE-ID ::= 503
id-Power-Local-Cell-Group-ID										ProtocolIE-ID ::= 504
id-PUSCH-Info-DM-Rqst												ProtocolIE-ID ::= 505
id-PUSCH-Info-DM-Rsp												ProtocolIE-ID ::= 506
id-PUSCH-Info-DM-Rprt												ProtocolIE-ID ::= 507
id-InitDL-Power														ProtocolIE-ID ::= 509
id-cellSyncBurstRepetitionPeriod									ProtocolIE-ID ::= 511
id-ReportCharacteristicsType-OnModification							ProtocolIE-ID ::= 512
id-SFNSFNMeasurementValueInformation								ProtocolIE-ID ::= 513
id-SFNSFNMeasurementThresholdInformation							ProtocolIE-ID ::= 514
id-TUTRANGPSMeasurementValueInformation								ProtocolIE-ID ::= 515
id-TUTRANGPSMeasurementThresholdInformation							ProtocolIE-ID ::= 516
id-Rx-Timing-Deviation-Value-LCR									ProtocolIE-ID ::= 520
id-RL-InformationResponse-LCR-RL-AdditionRspTDD						ProtocolIE-ID ::= 51
id-DL-PowerBalancing-Information									ProtocolIE-ID ::= 28
id-DL-PowerBalancing-ActivationIndicator							ProtocolIE-ID ::= 29
id-DL-PowerBalancing-UpdatedIndicator								ProtocolIE-ID ::= 30
id-CCTrCH-Initial-DL-Power-RL-SetupRqstTDD							ProtocolIE-ID ::= 517
id-CCTrCH-Initial-DL-Power-RL-AdditionRqstTDD						ProtocolIE-ID ::= 518
id-CCTrCH-Initial-DL-Power-RL-ReconfPrepTDD							ProtocolIE-ID ::= 519
id-IPDLParameter-Information-LCR-Cell-SetupRqstTDD					ProtocolIE-ID ::= 41
id-IPDLParameter-Information-LCR-Cell-ReconfRqstTDD 				ProtocolIE-ID ::= 42
id-HS-PDSCH-HS-SCCH-MaxPower-PSCH-ReconfRqst						ProtocolIE-ID ::= 522
id-HS-PDSCH-HS-SCCH-ScramblingCode-PSCH-ReconfRqst					ProtocolIE-ID ::= 523
id-HS-PDSCH-FDD-Code-Information-PSCH-ReconfRqst					ProtocolIE-ID ::= 524
id-HS-SCCH-FDD-Code-Information-PSCH-ReconfRqst						ProtocolIE-ID ::= 525
id-HS-PDSCH-TDD-Information-PSCH-ReconfRqst							ProtocolIE-ID ::= 526
id-Add-To-HS-SCCH-Resource-Pool-PSCH-ReconfRqst						ProtocolIE-ID ::= 527
id-Modify-HS-SCCH-Resource-Pool-PSCH-ReconfRqst						ProtocolIE-ID ::= 528
id-Delete-From-HS-SCCH-Resource-Pool-PSCH-ReconfRqst				ProtocolIE-ID ::= 529
id-bindingID														ProtocolIE-ID ::= 102
id-RL-Specific-DCH-Info												ProtocolIE-ID ::= 103
id-transportlayeraddress 											ProtocolIE-ID ::= 104
id-DelayedActivation 												ProtocolIE-ID ::= 231
id-DelayedActivationList-RL-ActivationCmdFDD						ProtocolIE-ID ::= 232
id-DelayedActivationInformation-RL-ActivationCmdFDD					ProtocolIE-ID ::= 233
id-DelayedActivationList-RL-ActivationCmdTDD						ProtocolIE-ID ::= 234
id-DelayedActivationInformation-RL-ActivationCmdTDD					ProtocolIE-ID ::= 235
id-neighbouringTDDCellMeasurementInformationLCR						ProtocolIE-ID ::= 58
id-SYNCDlCodeId-TransInitLCR-CellSyncInitiationRqstTDD				ProtocolIE-ID ::= 543
id-SYNCDlCodeId-MeasureInitLCR-CellSyncInitiationRqstTDD			ProtocolIE-ID ::= 544
id-SYNCDlCodeIdTransReconfInfoLCR-CellSyncReconfRqstTDD				ProtocolIE-ID ::= 545
id-SYNCDlCodeIdMeasReconfigurationLCR-CellSyncReconfRqstTDD			ProtocolIE-ID ::= 546
id-SYNCDlCodeIdMeasInfoList-CellSyncReconfRqstTDD					ProtocolIE-ID ::= 547
id-SyncDLCodeIdsMeasInfoList-CellSyncReprtTDD						ProtocolIE-ID ::= 548
id-SyncDLCodeIdThreInfoLCR											ProtocolIE-ID ::= 549
id-NSubCyclesPerCyclePeriod-CellSyncReconfRqstTDD					ProtocolIE-ID ::= 550
id-DwPCH-Power														ProtocolIE-ID ::= 551
id-AccumulatedClockupdate-CellSyncReprtTDD							ProtocolIE-ID ::= 552
id-Angle-Of-Arrival-Value-LCR										ProtocolIE-ID ::= 521
id-HSDSCH-FDD-Information											ProtocolIE-ID ::= 530
id-HSDSCH-FDD-Information-Response									ProtocolIE-ID ::= 531
id-HSDSCH-Information-to-Modify										ProtocolIE-ID ::= 534
id-HSDSCH-RNTI														ProtocolIE-ID ::= 535
id-HSDSCH-TDD-Information											ProtocolIE-ID ::= 536
id-HSDSCH-TDD-Information-Response									ProtocolIE-ID ::= 537
id-HSPDSCH-RL-ID													ProtocolIE-ID ::= 541
id-PrimCCPCH-RSCP-DL-PC-RqstTDD										ProtocolIE-ID ::= 542
id-Qth-Parameter													ProtocolIE-ID ::= 64
id-PDSCH-RL-ID														ProtocolIE-ID ::= 66
id-HSDSCH-RearrangeList-Bearer-RearrangeInd							ProtocolIE-ID ::= 553
id-UL-Synchronisation-Parameters-LCR								ProtocolIE-ID ::= 554
id-HSDSCH-FDD-Update-Information									ProtocolIE-ID ::= 555
id-HSDSCH-TDD-Update-Information									ProtocolIE-ID ::= 556
id-DL-DPCH-TimeSlotFormat-LCR-ModifyItem-RL-ReconfPrepTDD			ProtocolIE-ID ::= 558
id-UL-DPCH-TimeSlotFormat-LCR-ModifyItem-RL-ReconfPrepTDD			ProtocolIE-ID ::= 559
id-TDD-TPC-UplinkStepSize-LCR-RL-SetupRqstTDD						ProtocolIE-ID ::= 560
id-TDD-TPC-UplinkStepSize-LCR-RL-AdditionRqstTDD					ProtocolIE-ID ::= 561
id-TDD-TPC-DownlinkStepSize-RL-AdditionRqstTDD						ProtocolIE-ID ::= 562
id-TDD-TPC-UplinkStepSize-InformationAdd-LCR-RL-ReconfPrepTDD		ProtocolIE-ID ::= 563
id-TDD-TPC-UplinkStepSize-InformationModify-LCR-RL-ReconfPrepTDD	ProtocolIE-ID ::= 564
id-TDD-TPC-DownlinkStepSize-InformationModify-RL-ReconfPrepTDD		ProtocolIE-ID ::= 565
id-TDD-TPC-DownlinkStepSize-InformationAdd-RL-ReconfPrepTDD		ProtocolIE-ID ::= 566
id-CCTrCH-Maximum-DL-Power-RL-SetupRqstTDD							ProtocolIE-ID ::= 567
id-CCTrCH-Minimum-DL-Power-RL-SetupRqstTDD							ProtocolIE-ID ::= 568
id-CCTrCH-Maximum-DL-Power-RL-AdditionRqstTDD						ProtocolIE-ID ::= 569
id-CCTrCH-Minimum-DL-Power-RL-AdditionRqstTDD						ProtocolIE-ID ::= 570
id-CCTrCH-Maximum-DL-Power-InformationAdd-RL-ReconfPrepTDD			ProtocolIE-ID ::= 571
id-CCTrCH-Minimum-DL-Power-InformationAdd-RL-ReconfPrepTDD			ProtocolIE-ID ::= 572
id-CCTrCH-Maximum-DL-Power-InformationModify-RL-ReconfPrepTDD		ProtocolIE-ID ::= 573
id-CCTrCH-Minimum-DL-Power-InformationModify-RL-ReconfPrepTDD		ProtocolIE-ID ::= 574
id-Maximum-DL-Power-Modify-LCR-InformationModify-RL-ReconfPrepTDD	ProtocolIE-ID ::= 575
id-Minimum-DL-Power-Modify-LCR-InformationModify-RL-ReconfPrepTDD	ProtocolIE-ID ::= 576
id-DL-DPCH-LCR-InformationModify-ModifyList-RL-ReconfRqstTDD		ProtocolIE-ID ::= 577
id-CCTrCH-Maximum-DL-Power-InformationModify-RL-ReconfRqstTDD		ProtocolIE-ID ::= 578
id-CCTrCH-Minimum-DL-Power-InformationModify-RL-ReconfRqstTDD		ProtocolIE-ID ::= 579
id-Initial-DL-Power-TimeslotLCR-InformationItem						ProtocolIE-ID ::= 580
id-Maximum-DL-Power-TimeslotLCR-InformationItem						ProtocolIE-ID ::= 581
id-Minimum-DL-Power-TimeslotLCR-InformationItem						ProtocolIE-ID ::= 582
id-HS-DSCHProvidedBitRate											ProtocolIE-ID ::= 583
id-HS-DSCHRequiredPower												ProtocolIE-ID ::= 585
id-HS-DSCHRequiredPowerValue										ProtocolIE-ID ::= 586
id-TransmittedCarrierPowerOfAllCodesNotUsedForHS-PDSCHOrHS-SCCHTransmission	ProtocolIE-ID ::= 587
id-HS-SICH-Reception-Quality 										ProtocolIE-ID ::= 588
id-HS-SICH-Reception-Quality-Measurement-Value 						ProtocolIE-ID ::= 589
id-HSSICH-Info-DM-Rprt 												ProtocolIE-ID ::= 590
id-HSSICH-Info-DM-Rqst												ProtocolIE-ID ::= 591
id-HSSICH-Info-DM-Rsp												ProtocolIE-ID ::= 592
id-Best-Cell-Portions-Value											ProtocolIE-ID ::= 593
id-Primary-CPICH-Usage-for-Channel-Estimation						ProtocolIE-ID ::= 594
id-Secondary-CPICH-Information-Change								ProtocolIE-ID ::= 595
id-NumberOfReportedCellPortions										ProtocolIE-ID ::= 596
id-TimeslotISCP-LCR-InfoList-RL-ReconfPrepTDD						ProtocolIE-ID ::= 599
id-Unidirectional-DCH-Indicator										ProtocolIE-ID ::= 602
id-TimingAdjustmentValueLCR											ProtocolIE-ID ::= 603
id-multipleRL-dl-DPCH-InformationList								ProtocolIE-ID ::= 604
id-multipleRL-dl-DPCH-InformationModifyList							ProtocolIE-ID ::= 605
id-multipleRL-ul-DPCH-InformationList								ProtocolIE-ID ::= 606
id-multipleRL-ul-DPCH-InformationModifyList							ProtocolIE-ID ::= 607
id-RL-ID															ProtocolIE-ID ::= 608
id-SAT-Info-Almanac-ExtItem											ProtocolIE-ID ::= 609
id-HSDPA-Capability													ProtocolIE-ID ::= 610
id-HSDSCH-Resources-Information-AuditRsp							ProtocolIE-ID ::= 611
id-HSDSCH-Resources-Information-ResourceStatusInd					ProtocolIE-ID ::= 612
id-HSDSCH-MACdFlows-to-Add											ProtocolIE-ID ::= 613
id-HSDSCH-MACdFlows-to-Delete										ProtocolIE-ID ::= 614
id-HSDSCH-Information-to-Modify-Unsynchronised						ProtocolIE-ID ::= 615
id-TnlQos															ProtocolIE-ID ::= 616
id-PrimaryCCPCH-RSCP-Delta											ProtocolIE-ID ::= 623


END
