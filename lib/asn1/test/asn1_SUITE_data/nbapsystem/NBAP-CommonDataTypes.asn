-- **************************************************************
--
-- Common definitions
--
-- **************************************************************

NBAP-CommonDataTypes {
itu-t (0) identified-organization (4) etsi (0) mobileDomain (0) 
umts-Access (20) modules (3) nbap (2) version1 (1) nbap-CommonDataTypes (3)  }

DEFINITIONS AUTOMATIC TAGS ::= 

BEGIN

-- **************************************************************
--
-- Extension constants
--
-- **************************************************************

maxPrivateIEs 					INTEGER ::= 65535
maxProtocolExtensions 			INTEGER ::= 65535
maxProtocolIEs					INTEGER ::= 65535

-- **************************************************************
--
-- Common Data Types
--
-- **************************************************************

Criticality		::= ENUMERATED { reject, ignore, notify }

MessageDiscriminator	::= ENUMERATED { common, dedicated }

Presence		::= ENUMERATED { optional, conditional, mandatory }

PrivateIE-ID	::= CHOICE {
	local				INTEGER (0..maxPrivateIEs),
	global				OBJECT IDENTIFIER
}

ProcedureCode	::= INTEGER (0..255)

ProcedureID		::= SEQUENCE {
	procedureCode			ProcedureCode,
	ddMode					ENUMERATED { tdd, fdd, common, ... }
}

ProtocolIE-ID		::= INTEGER (0..maxProtocolIEs)

TransactionID 		::= CHOICE {
	shortTransActionId		INTEGER (0..127),
	longTransActionId		INTEGER (0..32767)
}

TriggeringMessage	::= ENUMERATED { initiating-message, successful-outcome, unsuccessfull-outcome, outcome }

END
