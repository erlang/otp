SeqExtension2 DEFINITIONS AUTOMATIC TAGS ::=
BEGIN

SeqExt66 ::= SEQUENCE {
  ...,
  i0 INTEGER (0..127) OPTIONAL,
  i1 INTEGER (0..127) OPTIONAL,
  i2 INTEGER (0..127) OPTIONAL,
  i3 INTEGER (0..127) OPTIONAL,
  i4 INTEGER (0..127) OPTIONAL,
  i5 INTEGER (0..127) OPTIONAL,
  i6 INTEGER (0..127) OPTIONAL,
  i7 INTEGER (0..127) OPTIONAL,
  i8 INTEGER (0..127) OPTIONAL,
  i9 INTEGER (0..127) OPTIONAL,
  i10 INTEGER (0..127) OPTIONAL,
  i11 INTEGER (0..127) OPTIONAL,
  i12 INTEGER (0..127) OPTIONAL,
  i13 INTEGER (0..127) OPTIONAL,
  i14 INTEGER (0..127) OPTIONAL,
  i15 INTEGER (0..127) OPTIONAL,
  i16 INTEGER (0..127) OPTIONAL,
  i17 INTEGER (0..127) OPTIONAL,
  i18 INTEGER (0..127) OPTIONAL,
  i19 INTEGER (0..127) OPTIONAL,
  i20 INTEGER (0..127) OPTIONAL,
  i21 INTEGER (0..127) OPTIONAL,
  i22 INTEGER (0..127) OPTIONAL,
  i23 INTEGER (0..127) OPTIONAL,
  i24 INTEGER (0..127) OPTIONAL,
  i25 INTEGER (0..127) OPTIONAL,
  i26 INTEGER (0..127) OPTIONAL,
  i27 INTEGER (0..127) OPTIONAL,
  i28 INTEGER (0..127) OPTIONAL,
  i29 INTEGER (0..127) OPTIONAL,
  i30 INTEGER (0..127) OPTIONAL,
  i31 INTEGER (0..127) OPTIONAL,
  i32 INTEGER (0..127) OPTIONAL,
  i33 INTEGER (0..127) OPTIONAL,
  i34 INTEGER (0..127) OPTIONAL,
  i35 INTEGER (0..127) OPTIONAL,
  i36 INTEGER (0..127) OPTIONAL,
  i37 INTEGER (0..127) OPTIONAL,
  i38 INTEGER (0..127) OPTIONAL,
  i39 INTEGER (0..127) OPTIONAL,
  i40 INTEGER (0..127) OPTIONAL,
  i41 INTEGER (0..127) OPTIONAL,
  i42 INTEGER (0..127) OPTIONAL,
  i43 INTEGER (0..127) OPTIONAL,
  i44 INTEGER (0..127) OPTIONAL,
  i45 INTEGER (0..127) OPTIONAL,
  i46 INTEGER (0..127) OPTIONAL,
  i47 INTEGER (0..127) OPTIONAL,
  i48 INTEGER (0..127) OPTIONAL,
  i49 INTEGER (0..127) OPTIONAL,
  i50 INTEGER (0..127) OPTIONAL,
  i51 INTEGER (0..127) OPTIONAL,
  i52 INTEGER (0..127) OPTIONAL,
  i53 INTEGER (0..127) OPTIONAL,
  i54 INTEGER (0..127) OPTIONAL,
  i55 INTEGER (0..127) OPTIONAL,
  i56 INTEGER (0..127) OPTIONAL,
  i57 INTEGER (0..127) OPTIONAL,
  i58 INTEGER (0..127) OPTIONAL,
  i59 INTEGER (0..127) OPTIONAL,
  i60 INTEGER (0..127) OPTIONAL,
  i61 INTEGER (0..127) OPTIONAL,
  i62 INTEGER (0..127) OPTIONAL,
  i63 INTEGER (0..127) OPTIONAL,
  i64 INTEGER (0..127) OPTIONAL,
  i65 INTEGER (0..127) OPTIONAL
}

SeqExt130 ::= SEQUENCE {
  ...,
  i0 INTEGER (0..255) OPTIONAL,
  i1 INTEGER (0..255) OPTIONAL,
  i2 INTEGER (0..255) OPTIONAL,
  i3 INTEGER (0..255) OPTIONAL,
  i4 INTEGER (0..255) OPTIONAL,
  i5 INTEGER (0..255) OPTIONAL,
  i6 INTEGER (0..255) OPTIONAL,
  i7 INTEGER (0..255) OPTIONAL,
  i8 INTEGER (0..255) OPTIONAL,
  i9 INTEGER (0..255) OPTIONAL,
  i10 INTEGER (0..255) OPTIONAL,
  i11 INTEGER (0..255) OPTIONAL,
  i12 INTEGER (0..255) OPTIONAL,
  i13 INTEGER (0..255) OPTIONAL,
  i14 INTEGER (0..255) OPTIONAL,
  i15 INTEGER (0..255) OPTIONAL,
  i16 INTEGER (0..255) OPTIONAL,
  i17 INTEGER (0..255) OPTIONAL,
  i18 INTEGER (0..255) OPTIONAL,
  i19 INTEGER (0..255) OPTIONAL,
  i20 INTEGER (0..255) OPTIONAL,
  i21 INTEGER (0..255) OPTIONAL,
  i22 INTEGER (0..255) OPTIONAL,
  i23 INTEGER (0..255) OPTIONAL,
  i24 INTEGER (0..255) OPTIONAL,
  i25 INTEGER (0..255) OPTIONAL,
  i26 INTEGER (0..255) OPTIONAL,
  i27 INTEGER (0..255) OPTIONAL,
  i28 INTEGER (0..255) OPTIONAL,
  i29 INTEGER (0..255) OPTIONAL,
  i30 INTEGER (0..255) OPTIONAL,
  i31 INTEGER (0..255) OPTIONAL,
  i32 INTEGER (0..255) OPTIONAL,
  i33 INTEGER (0..255) OPTIONAL,
  i34 INTEGER (0..255) OPTIONAL,
  i35 INTEGER (0..255) OPTIONAL,
  i36 INTEGER (0..255) OPTIONAL,
  i37 INTEGER (0..255) OPTIONAL,
  i38 INTEGER (0..255) OPTIONAL,
  i39 INTEGER (0..255) OPTIONAL,
  i40 INTEGER (0..255) OPTIONAL,
  i41 INTEGER (0..255) OPTIONAL,
  i42 INTEGER (0..255) OPTIONAL,
  i43 INTEGER (0..255) OPTIONAL,
  i44 INTEGER (0..255) OPTIONAL,
  i45 INTEGER (0..255) OPTIONAL,
  i46 INTEGER (0..255) OPTIONAL,
  i47 INTEGER (0..255) OPTIONAL,
  i48 INTEGER (0..255) OPTIONAL,
  i49 INTEGER (0..255) OPTIONAL,
  i50 INTEGER (0..255) OPTIONAL,
  i51 INTEGER (0..255) OPTIONAL,
  i52 INTEGER (0..255) OPTIONAL,
  i53 INTEGER (0..255) OPTIONAL,
  i54 INTEGER (0..255) OPTIONAL,
  i55 INTEGER (0..255) OPTIONAL,
  i56 INTEGER (0..255) OPTIONAL,
  i57 INTEGER (0..255) OPTIONAL,
  i58 INTEGER (0..255) OPTIONAL,
  i59 INTEGER (0..255) OPTIONAL,
  i60 INTEGER (0..255) OPTIONAL,
  i61 INTEGER (0..255) OPTIONAL,
  i62 INTEGER (0..255) OPTIONAL,
  i63 INTEGER (0..255) OPTIONAL,
  i64 INTEGER (0..255) OPTIONAL,
  i65 INTEGER (0..255) OPTIONAL,
  i66 INTEGER (0..255) OPTIONAL,
  i67 INTEGER (0..255) OPTIONAL,
  i68 INTEGER (0..255) OPTIONAL,
  i69 INTEGER (0..255) OPTIONAL,
  i70 INTEGER (0..255) OPTIONAL,
  i71 INTEGER (0..255) OPTIONAL,
  i72 INTEGER (0..255) OPTIONAL,
  i73 INTEGER (0..255) OPTIONAL,
  i74 INTEGER (0..255) OPTIONAL,
  i75 INTEGER (0..255) OPTIONAL,
  i76 INTEGER (0..255) OPTIONAL,
  i77 INTEGER (0..255) OPTIONAL,
  i78 INTEGER (0..255) OPTIONAL,
  i79 INTEGER (0..255) OPTIONAL,
  i80 INTEGER (0..255) OPTIONAL,
  i81 INTEGER (0..255) OPTIONAL,
  i82 INTEGER (0..255) OPTIONAL,
  i83 INTEGER (0..255) OPTIONAL,
  i84 INTEGER (0..255) OPTIONAL,
  i85 INTEGER (0..255) OPTIONAL,
  i86 INTEGER (0..255) OPTIONAL,
  i87 INTEGER (0..255) OPTIONAL,
  i88 INTEGER (0..255) OPTIONAL,
  i89 INTEGER (0..255) OPTIONAL,
  i90 INTEGER (0..255) OPTIONAL,
  i91 INTEGER (0..255) OPTIONAL,
  i92 INTEGER (0..255) OPTIONAL,
  i93 INTEGER (0..255) OPTIONAL,
  i94 INTEGER (0..255) OPTIONAL,
  i95 INTEGER (0..255) OPTIONAL,
  i96 INTEGER (0..255) OPTIONAL,
  i97 INTEGER (0..255) OPTIONAL,
  i98 INTEGER (0..255) OPTIONAL,
  i99 INTEGER (0..255) OPTIONAL,
  i100 INTEGER (0..255) OPTIONAL,
  i101 INTEGER (0..255) OPTIONAL,
  i102 INTEGER (0..255) OPTIONAL,
  i103 INTEGER (0..255) OPTIONAL,
  i104 INTEGER (0..255) OPTIONAL,
  i105 INTEGER (0..255) OPTIONAL,
  i106 INTEGER (0..255) OPTIONAL,
  i107 INTEGER (0..255) OPTIONAL,
  i108 INTEGER (0..255) OPTIONAL,
  i109 INTEGER (0..255) OPTIONAL,
  i110 INTEGER (0..255) OPTIONAL,
  i111 INTEGER (0..255) OPTIONAL,
  i112 INTEGER (0..255) OPTIONAL,
  i113 INTEGER (0..255) OPTIONAL,
  i114 INTEGER (0..255) OPTIONAL,
  i115 INTEGER (0..255) OPTIONAL,
  i116 INTEGER (0..255) OPTIONAL,
  i117 INTEGER (0..255) OPTIONAL,
  i118 INTEGER (0..255) OPTIONAL,
  i119 INTEGER (0..255) OPTIONAL,
  i120 INTEGER (0..255) OPTIONAL,
  i121 INTEGER (0..255) OPTIONAL,
  i122 INTEGER (0..255) OPTIONAL,
  i123 INTEGER (0..255) OPTIONAL,
  i124 INTEGER (0..255) OPTIONAL,
  i125 INTEGER (0..255) OPTIONAL,
  i126 INTEGER (0..255) OPTIONAL,
  i127 INTEGER (0..255) OPTIONAL,
  i128 INTEGER (0..255) OPTIONAL,
  i129 INTEGER (0..255) OPTIONAL
}

END
