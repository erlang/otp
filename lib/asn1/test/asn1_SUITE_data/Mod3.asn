Mod3 DEFINITIONS AUTOMATIC TAGS ::=

BEGIN

IMPORTS
    Name
    FROM Mod4
    Lang, Inhabitant,FirstName,FamilyName
    FROM Mod2
    TS, RFS, WS, HS
    FROM Mod5;

Stat ::= SEQUENCE {
  tempstat TS,
  rainfallstat RFS,
  windstat  WS,
  humiditystat HS
}

Country ::= SEQUENCE{
  name Name,
  language Lang
}

RegionName ::= Name
Inhabitants ::= SEQUENCE OF Inhabitant

PersonName ::= SEQUENCE {
  name1 FirstName,
  name2 FamilyName
}

END
