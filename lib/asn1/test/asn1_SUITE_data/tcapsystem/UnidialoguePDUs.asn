-- Generated by Asnp, the pretty-printer of France Telecom R&D (http://asn1.elibel.tm.fr/asnp/)
-- Module UnidialoguePDUs (Q.773:06/1997)
UnidialoguePDUs {itu-t recommendation q 773 modules(2) unidialoguePDUs(3)
  version1(1)} DEFINITIONS ::=
BEGIN

EXPORTS uniDialogue-as-id, UniDialoguePDU;

-- Abstract syntax name for unstructured dialogue APDUs
uniDialogue-as-id OBJECT IDENTIFIER ::=
  {itu-t recommendation q 773 as(1) unidialogue-as(2) version1(1)}

UniDialoguePDU ::= CHOICE {unidialoguePDU  AUDT-apdu
}

AUDT-apdu ::= [APPLICATION 0] IMPLICIT SEQUENCE {
  protocol-version
    [0] IMPLICIT BIT STRING {version1(0)} DEFAULT {version1},
  application-context-name  [1]  OBJECT IDENTIFIER,
  user-information          [30] IMPLICIT SEQUENCE OF EXTERNAL OPTIONAL
}

END -- UNIDialoguePDU

-- Generated by Asnp, the ASN.1 pretty-printer of France Telecom R&D
