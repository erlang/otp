--
-- %CopyrightBegin%
--
-- SPDX-License-Identifier: Apache-2.0
--
-- Copyright Ericsson AB 2013-2026. All Rights Reserved.
--
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
--
-- %CopyrightEnd%
--

EnumExt DEFINITIONS AUTOMATIC TAGS ::=
BEGIN

Ext ::= ENUMERATED {
	blue(0),
	red(1),
	green(2),
	...
}

Ext1 ::= ENUMERATED {
	blue(0),
	red(1),
	green(2),
	...,
	orange(7),
        black(8),
	magenta(9)
}

SubExt1 ::= Ext1 ( blue | orange | black )

Noext ::= ENUMERATED {
	blue(0),
	red(1),
	green(2)
}

Globalstate ::= ENUMERATED {def(1),com(2),preop(3),oper(4),noop(5),fail(6)}

SpecialAtoms ::= ENUMERATED {null(1),true(2),false(3)}

Seq ::= SEQUENCE {
   e Ext1,
   i INTEGER
}

EnumExtBig ::= ENUMERATED {
  base,
  ...,
  e00,e01,e02,e03,e04,e05,e06,e07,e08,e09,e0a,e0b,e0c,e0d,e0e,e0f,
  e10,e11,e12,e13,e14,e15,e16,e17,e18,e19,e1a,e1b,e1c,e1d,e1e,e1f,
  e20,e21,e22,e23,e24,e25,e26,e27,e28,e29,e2a,e2b,e2c,e2d,e2e,e2f,
  e30,e31,e32,e33,e34,e35,e36,e37,e38,e39,e3a,e3b,e3c,e3d,e3e,e3f,
  e40,e41,e42,e43,e44,e45,e46,e47,e48,e49,e4a,e4b,e4c,e4d,e4e,e4f,
  e50,e51,e52,e53,e54,e55,e56,e57,e58,e59,e5a,e5b,e5c,e5d,e5e,e5f,
  e60,e61,e62,e63,e64,e65,e66,e67,e68,e69,e6a,e6b,e6c,e6d,e6e,e6f,
  e70,e71,e72,e73,e74,e75,e76,e77,e78,e79,e7a,e7b,e7c,e7d,e7e,e7f,
  e80
}

SeqBig ::= SEQUENCE {
  b BOOLEAN,
  e EnumExtBig,
  i INTEGER
}

EnumSkip ::= ENUMERATED {a(2), ..., b, c, d, e, f}

END
