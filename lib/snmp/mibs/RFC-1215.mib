-- %CopyrightBegin%
--
-- SPDX-License-Identifier: LicenseRef-IETF-MIB
--
-- Copyright (C) The Internet Society (1991).  All Rights Reserved.
-- Copyright Ericsson AB 2009-2025. All Rights Reserved.
--
-- MIB modules published in IETF RFCs prior to the adoption of BCP 78 (such as
-- RFC 1158) are considered to be freely copyable and usable for implementation
-- and interoperability purposes. No explicit license was provided, but the IETF
-- intended for MIB code to be reusable and modifiable as necessary.
--
-- This interpretation is based on historical practice and later IETF
-- clarification that such material was meant to be in the public domain or
-- under permissive terms.
--
-- %CopyrightEnd%

RFC-1215 DEFINITIONS ::= BEGIN

IMPORTS
        ObjectName
    FROM RFC1155-SMI;
 
TRAP-TYPE MACRO ::=
BEGIN
    TYPE NOTATION ::=
                  "ENTERPRISE" value (enterprise OBJECT IDENTIFIER)
                  VarPart
                  DescrPart
                  ReferPart
    VALUE NOTATION ::=
                  value (VALUE INTEGER)
    VarPart ::=
                  "VARIABLES" "{" VarTypes "}"
                | empty
    VarTypes ::=
                  VarType | VarTypes "," VarType
    VarType ::=
                  value (vartype ObjectName)
    DescrPart ::=
                 "DESCRIPTION" value (description DisplayString)
               | empty
    ReferPart ::=
                 "REFERENCE" value (reference DisplayString)
               | empty
END
