-- 
-- %CopyrightBegin%
-- 
-- SPDX-License-Identifier: Apache-2.0
--
-- Copyright Ericsson AB 2025-2025. All Rights Reserved.
-- 
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- 
-- %CopyrightEnd%

-- This file is intended for 'basic types' in general, but currently only
-- contains (integer) types from the SNMPv2-SMI.
--
-- This (ASN.1) spec contains (some of the) types from the SNMPv2-SMI mib:
-- - 0 (64) IpAddress
-- + 1 (65) Counter32
-- - 2 (..) Gauge32 (same as Unsigned32, even the same tag)
-- + 2 (66) Unsigned32
-- + 3 (67) TimeTicks
-- - 4 (68) Opaque
-- + 6 (70) Counter64

SNMP-PDUS-BASIC DEFINITIONS ::=
BEGIN

-- 65
Counter32  ::= [APPLICATION 1] IMPLICIT INTEGER (0..4294967295)

-- 66
Unsigned32 ::= [APPLICATION 2] IMPLICIT INTEGER (0..4294967295)

-- 67
TimeTicks  ::= [APPLICATION 3] IMPLICIT INTEGER (0..4294967295)

-- 70
Counter64  ::= [APPLICATION 6] IMPLICIT INTEGER (0..18446744073709551615)

END
