-- %CopyrightBegin%
--
-- SPDX-License-Identifier: Apache-2.0
-- 
-- Copyright Ericsson AB 1996-2025. All Rights Reserved.
-- 
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- 
-- %CopyrightEnd%

          Klas1 DEFINITIONS ::= BEGIN
 
          IMPORTS
                  OBJECT-TYPE
                          FROM RFC-1212;
 
          klas1       OBJECT IDENTIFIER ::= { private 7 }
 
           DisplayString ::=
              OCTET STRING


	Q2 ::= DisplayString (SIZE (0..25))

	  RowStatus ::= 
                INTEGER {
                         -- the following two values are states:
                         -- these values may be read or written
                         active(1),
                         notInService(2),

                         -- the following value is a state:
                         -- this value may be read, but not written
                         notReady(3),

                         -- the following three values are
                         -- actions: these values may be written,
                         --   but are never read
                         createAndGo(4),
                         createAndWait(5),
                         destroy(6)
                      }


          fint OBJECT-TYPE
              SYNTAX  INTEGER
              ACCESS  read-write
              STATUS  mandatory
              DESCRIPTION
                      "A textual description of the entity.  This value
                      printable ASCII characters."
              ::= { klas1 0 1 }

          fname OBJECT-TYPE
              SYNTAX  DisplayString (SIZE (0..255))
              ACCESS  read-write
              STATUS  mandatory
              DESCRIPTION
                      "A textual description of the entity.  This value
                      printable ASCII characters."
              ::= { klas1 1 }
 
          friendsTable OBJECT-TYPE
              SYNTAX  SEQUENCE OF FriendsEntry
              ACCESS  not-accessible
              STATUS  mandatory
              DESCRIPTION
                      "A list of klas friends."
              ::= { klas1 4 }
 
          friendsEntry OBJECT-TYPE
              SYNTAX  FriendsEntry
              ACCESS  not-accessible
              STATUS  mandatory
              DESCRIPTION
                      "nope"
              INDEX   { fIndex }
              ::= { friendsTable 1 }
 
          FriendsEntry ::=
              SEQUENCE {
			fIndex
                      INTEGER,
                   fName
                      OCTET STRING,
                   fStatus
                      INTEGER              }
 
          fIndex OBJECT-TYPE
              SYNTAX  INTEGER
              ACCESS  not-accessible
              STATUS  mandatory
               DESCRIPTION
                      "number of friend"
              ::= { friendsEntry 1 }
 
          fName OBJECT-TYPE
              SYNTAX  OCTET STRING (SIZE (0..255))
              ACCESS  read-write
              STATUS  mandatory
              DESCRIPTION
                      "Name of friend"
              ::= { friendsEntry 2 }

           fStatus OBJECT-TYPE
              SYNTAX      RowStatus
              ACCESS      read-write
              STATUS      mandatory
              DESCRIPTION
                      "The status of this conceptual row."
              ::= { friendsEntry 3 }

          authenticationFajlure TRAP-TYPE
              ENTERPRISE  klas1
              DESCRIPTION
                          "An authenticationFailure trap signifies that
                          the sending protocol entity is the addressee
                          of a protocol message that is not properly
                          authenticated.  While implementations of the
                          SNMP must be capable of generating this trap,
                          they must also be capable of suppressing the
                          emission of such traps via an implementation-
                          specific mechanism."
              ::= 4


          END
