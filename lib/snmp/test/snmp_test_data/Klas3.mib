-- %CopyrightBegin%
--
-- SPDX-License-Identifier: Apache-2.0
-- 
-- Copyright Ericsson AB 1996-2025. All Rights Reserved.
-- 
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- 
-- %CopyrightEnd%

          Klas3 DEFINITIONS ::= BEGIN
 
-- This MIB is used for testing the undo phase

          IMPORTS
                  mib-2 FROM RFC1213-MIB
                  RowStatus FROM STANDARD-MIB
                  OBJECT-TYPE
                          FROM RFC-1212;
 
          klas3       OBJECT IDENTIFIER ::= { mib-2 8 }
 
           DisplayString ::=
              OCTET STRING

          fname3 OBJECT-TYPE
              SYNTAX  DisplayString (SIZE (0..255))
              ACCESS  read-write
              STATUS  mandatory
              DESCRIPTION
                      "A textual description of the entity.  This value
                      printable ASCII characters."
              ::= { klas3 1 }
 
          fname4 OBJECT-TYPE
		SYNTAX INTEGER {
		none(1),
		snmpTrap(3)
		}
              ACCESS  read-only
              STATUS  mandatory
              DESCRIPTION
                      "A textual description of the entity.  This value
                      printable ASCII characters."
              ::= { klas3 2 }
 
	   

          END
