-- %CopyrightBegin%
--
-- SPDX-License-Identifier: Apache-2.0
-- 
-- Copyright Ericsson AB 2000-2025. All Rights Reserved.
-- 
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- 
-- %CopyrightEnd%

OTP14145-MIB DEFINITIONS ::= BEGIN

IMPORTS
       MODULE-IDENTITY, OBJECT-TYPE,
       mib-2      FROM SNMPv2-SMI
       InetAddressType, InetAddress     FROM INET-ADDRESS-MIB
       MODULE-COMPLIANCE, OBJECT-GROUP  FROM SNMPv2-CONF;

testMibId MODULE-IDENTITY
       LAST-UPDATED "200608210000Z"  -- 21 August 2006
       ORGANIZATION "a"
       CONTACT-INFO "a"
       DESCRIPTION "a"
       REVISION "200608210000Z"  -- 21 August 2006
       DESCRIPTION "a"
       ::= { mib-2 67 }

testObj OBJECT-TYPE
       SYNTAX InetAddressType
       -- SYNTAX InetAddress
       MAX-ACCESS read-only
       STATUS current
       DESCRIPTION "a"
       ::= { testMibId 2 }

testObjId OBJECT IDENTIFIER ::= { testMibId 3 }

testMibCompliance MODULE-COMPLIANCE
            STATUS  current
            DESCRIPTION "a"
            MODULE
            OBJECT testObj
            SYNTAX InetAddressType { ipv4(1), ipv6(2) }
            -- SYNTAX InetAddress ( SIZE(4|16) )
            DESCRIPTION "a"
            ::= { testMibId 4 }

testObjGroup OBJECT-GROUP
  OBJECTS { testObj }
  STATUS current
  DESCRIPTION "a"
  ::= { testObjId 1 }

END
