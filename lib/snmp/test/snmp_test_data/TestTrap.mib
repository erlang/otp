-- %CopyrightBegin%
--
-- SPDX-License-Identifier: Apache-2.0
-- 
-- Copyright Ericsson AB 1996-2025. All Rights Reserved.
-- 
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- 
-- %CopyrightEnd%

TestTrap DEFINITIONS ::= BEGIN
 
          IMPORTS
                  Counter, TimeTicks, IpAddress
                      FROM RFC1155-SMI
                  OBJECT-TYPE
                      FROM RFC-1212
                  mgmt, NetworkAddress, IpAddress, Counter, Gauge,
                          TimeTicks
                      FROM RFC1155-SMI
                  DisplayString, snmp, system,sysContact, ifIndex
                      FROM RFC1213-MIB
                  OBJECT-TYPE
                          FROM RFC-1212;
 


          testTrap1 TRAP-TYPE
              ENTERPRISE  snmp
              VARIABLES   { sysContact }
              DESCRIPTION
		""
              ::= 1
 
          testTrap2 TRAP-TYPE
              ENTERPRISE  system
              VARIABLES   { sysContact }
              DESCRIPTION
		""
              ::= 1

 
          linkDown TRAP-TYPE
              ENTERPRISE  snmp
              VARIABLES   { ifIndex }
              DESCRIPTION
                          "A linkDown trap signifies that the sending
                          protocol entity recognizes a failure in one of
                          the communication links represented in the
                          agent's configuration."
              ::= 2
 
 
END
