-- %CopyrightBegin%
--
-- SPDX-License-Identifier: Apache-2.0
-- 
-- Copyright Ericsson AB 2002-2025. All Rights Reserved.
-- 
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- 
-- %CopyrightEnd%

-- ERICSSON-TOP-MIB:  Top-level MIB for Ericsson AB's 
-- 193 branch of the enterprise MIB tree.
--
-- ERICSSON-TOP-MIB.mib,v 1.1 2002/06/12 13:14:57 epkpart Exp
--
-- ERICSSON-TOP-MIB.mib,v
-- Revision 1.1  2002/06/12 13:14:57  epkpart
-- Initial revision
--
-- 
-- Copyright (c) 2002 by Ericsson AB
-- All rights reserved.
-- 

ERICSSON-TOP-MIB DEFINITIONS ::= BEGIN

IMPORTS
    MODULE-IDENTITY, enterprises
        FROM SNMPv2-SMI;

ericsson MODULE-IDENTITY
    LAST-UPDATED
        "200205280000Z"
    ORGANIZATION
        "Ericsson AB "
    CONTACT-INFO
        "David Partain <david.partain@ericsson.com>
	 or
	 whoever is currently responsible for the Ericsson
	 enterprise MIB tree branch (enterprises.193)."
    DESCRIPTION
        "This very small module is made available so that
	developers within the Ericsson community can import the
	'ericsson' name into their own MIB modules."
    ::= { enterprises 193 }
END
