-- %CopyrightBegin%
--
-- SPDX-License-Identifier: Apache-2.0
-- 
-- Copyright Ericsson AB 2000-2025. All Rights Reserved.
-- 
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- 
-- %CopyrightEnd%

OTP14196-MIB DEFINITIONS ::= BEGIN

IMPORTS
    MODULE-IDENTITY, OBJECT-TYPE, snmpModules, mib-2
        FROM SNMPv2-SMI
    TEXTUAL-CONVENTION
        FROM SNMPv2-TC
    OBJECT-GROUP
        FROM SNMPv2-CONF
    ;

otp14196MIB MODULE-IDENTITY
    LAST-UPDATED "1004210000Z"
    ORGANIZATION ""
    CONTACT-INFO
	""
    DESCRIPTION
            "Test mib for OTP-14196"
    ::= { snmpModules 1 }

testCompliances OBJECT IDENTIFIER ::= { otp14196MIB 1 }
test   OBJECT IDENTIFIER ::= { mib-2 15 }

typeA OBJECT-TYPE
    SYNTAX TypeAType
    MAX-ACCESS  accessible-for-notify
    STATUS current
    DESCRIPTION
	"Test type for OTP-14196"
    ::= { test 4711 }

TypeAType ::= TEXTUAL-CONVENTION
    STATUS current
    DESCRIPTION
	""
    SYNTAX INTEGER

testGroups OBJECT IDENTIFIER ::= { testCompliances 1 }

testGroupA OBJECT-GROUP
    OBJECTS { typeA }
    STATUS current
    DESCRIPTION
	""
    ::= { testGroups 17 }

END
