-- %CopyrightBegin%
--
-- SPDX-License-Identifier: Apache-2.0
-- 
-- Copyright Ericsson AB 1996-2025. All Rights Reserved.
-- 
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- 
-- %CopyrightEnd%

EX1-MIBv2 DEFINITIONS ::= BEGIN

IMPORTS
    MODULE-IDENTITY, OBJECT-TYPE, NOTIFICATION-TYPE,
    Integer32, snmpModules ,experimental
        FROM SNMPv2-SMI
    MODULE-COMPLIANCE, OBJECT-GROUP, NOTIFICATION-GROUP
        FROM SNMPv2-CONF
    DisplayString 
	FROM SNMPv2-TC
    RowStatus
	FROM STANDARD-MIB;
	

exampleModule MODULE-IDENTITY
	LAST-UPDATED "0005290000Z"
	ORGANIZATION "Erlang"
	CONTACT-INFO " test mib
			Ericsson Utvecklings AB
			Open System
			Box 1505
			SE-125 25 ÄLVSJÖ"

	DESCRIPTION 
		" Objects for management "
	REVISION   "0005290000Z"
	DESCRIPTION 
		"The initial version"
	::= { snmpModules 1 }

example1 OBJECT IDENTIFIER ::= { experimental 7}
 

         myName OBJECT-TYPE
              SYNTAX      DisplayString
              MAX-ACCESS  read-write
              STATUS  current
              DESCRIPTION
                      "My own name"
              ::= { example1 1 }
 
          friendsTable OBJECT-TYPE
              SYNTAX  SEQUENCE OF FriendsEntry
              MAX-ACCESS  not-accessible
              STATUS   current
              DESCRIPTION
                      "A list of friends."
              ::= { example1 4 }
 
          friendsEntry OBJECT-TYPE
              SYNTAX  FriendsEntry
              MAX-ACCESS  not-accessible
              STATUS  current
              DESCRIPTION
                      ""
              INDEX   { fIndex }
              ::= { friendsTable 1 }
 
          FriendsEntry ::= SEQUENCE {
		fIndex   INTEGER,
                fName    DisplayString,
                fAddress DisplayString,
                fStatus  RowStatus
		}
 
          fIndex OBJECT-TYPE
              SYNTAX      INTEGER
              MAX-ACCESS  read-only
              STATUS      current
               DESCRIPTION
                      "number of friend"
              ::= { friendsEntry 1 }
 
          fName OBJECT-TYPE
              SYNTAX      DisplayString (SIZE (0..255))
              MAX-ACCESS  read-write
              STATUS      deprecated
              DESCRIPTION
                      "Name of  a friend"
              ::= { friendsEntry 2 }

          fAddress OBJECT-TYPE
              SYNTAX      DisplayString (SIZE (0..255))
              MAX-ACCESS  read-write
              STATUS      current
              DESCRIPTION
                      "Address of a friend"
              ::= { friendsEntry 3 }

           fStatus OBJECT-TYPE
              SYNTAX      RowStatus
              MAX-ACCESS  read-write
              STATUS      current
              DESCRIPTION
                      "The status of this conceptual row."
              ::= { friendsEntry 4 }

friendGroup OBJECT-GROUP
	OBJECTS { myName, fIndex, fName,fAddress, fStatus } 
	STATUS current
	DESCRIPTION " A object group"
	::= { example1 2 }

END
